--/****************************************************************************
--
--  Copyright (C), 2011-2016, Huawei Tech. Co., Ltd.
--
--*****************************************************************************
--  File Name     : HUAWEI-SERVER-IBMC-MIB.mib
--
--****************************************************************************/

HUAWEI-SERVER-IBMC-MIB DEFINITIONS ::= BEGIN
	IMPORTS    MODULE-IDENTITY, OBJECT-TYPE, NOTIFICATION-TYPE,Integer32
                   FROM SNMPv2-SMI
               Counter32,
               IpAddress,
               Gauge32,
               Unsigned32,
               TimeTicks,
               Opaque,
               Counter64
                   FROM SNMPv2-SMI
               RowStatus,
               StorageType
                   FROM SNMPv2-TC
               SnmpAdminString
                   FROM SNMP-FRAMEWORK-MIB
               enterprises
                   FROM SNMPv2-SMI 
               DisplayString
    			   FROM RFC1213-MIB;

        huawei OBJECT IDENTIFIER ::= { enterprises 2011 } 
        products OBJECT IDENTIFIER ::= { huawei 2 }
        hwServer OBJECT IDENTIFIER ::={ products 235 }
        hwBMC OBJECT IDENTIFIER ::={ hwServer 1 }        
       
        hwiBMC MODULE-IDENTITY
              LAST-UPDATED 	"201110250000Z"  
              ORGANIZATION 	"Huawei Technologies Co.,Ltd."
              CONTACT-INFO
              				" http://www.huawei.com
                   	          Zip:518129   E-mail:support@huawei.com "    
              DESCRIPTION
                            "The HUAWEI-SERVER-IBMC-MIB contains objects to Manage the server."
              ::= { hwBMC 1 }

--    ****** uspSystem Location ******************************* 
		system OBJECT IDENTIFIER ::= { hwiBMC 1 }


		systemHealth OBJECT-TYPE
			SYNTAX INTEGER
				{
				ok(1),
				minor(2),
				major(3), 
				critical(4)
				}
			MAX-ACCESS read-only
			STATUS current
			DESCRIPTION
				"systemHealth information about system present state of health. 
				This value will be one of the following:
				(1-OK, 2-Minor, 3-Major, 4-Critical)"
			::= { system 1 }


		systemBootsequence OBJECT-TYPE
			SYNTAX INTEGER
				{
				noOverride(1),
				pxe(2),				
				hdd(3),
				cdDvd(4),
				floppyPrimaryRemovableMedia(5),
				unspecified(6),
				biossetup(7)
				}
			MAX-ACCESS read-write
			STATUS current
			DESCRIPTION
				"Decide the system's first boot device.
				 1  - No override
				 2  - Force PXE
				 3  - Force boot from default Hard-drive
				 4  - Force boot from default CD/DVD
				 5  - Force boot from Floppy/primary removable media
				 6  - boot flags valid. The bit should be set to indicate that valid flag data is present. 
					  This bit may be automatically cleared based on the boot flag valid bit clearing 
					  parameter, above.(This option is read-only.)
				 7 -  Force boot into BIOS SETUP
			     The default value is 6 (unspecified)"
			::= { system 2 }    


		systemTime OBJECT-TYPE
			SYNTAX DisplayString
			MAX-ACCESS read-only
			STATUS current
			DESCRIPTION
				"systemTime information about iBMC system time, based on UTC.
				the value such as (yyyy-mm-dd hh:mm:ss)."
			::= { system 3 }  


		systemTimeZone OBJECT-TYPE
			SYNTAX Integer32 (-720..840)
			MAX-ACCESS read-write
			STATUS current
			DESCRIPTION
				"systemTimeZone information about iBMC time zone.
				The value is in [-720, 840]."
			::= { system 4 }	
        

		safepowerofftime OBJECT-TYPE
			SYNTAX Integer32
			MAX-ACCESS read-write
			STATUS current
			DESCRIPTION
				"The system safe poweroff time, the value 0 indicates non-timeout."
			::= { system 5 }   
			   

		deviceName OBJECT-TYPE
			SYNTAX DisplayString
			MAX-ACCESS read-only
			STATUS current
			DESCRIPTION
				"The device name value between 1 to 63 characters."
			::= { system 6 } 
			

		deviceSerialNo OBJECT-TYPE
			SYNTAX DisplayString
			MAX-ACCESS read-only
			STATUS current
			DESCRIPTION
				"The device serial number value between 1 to 63 characters."
			::= { system 7 }   
			


		powerOnPolicy OBJECT-TYPE
			SYNTAX INTEGER
				{
				stayoff(1),
				restorePreviousState(2),				
				turnon(3)
				}
			MAX-ACCESS read-write
			STATUS current
			DESCRIPTION
				"1  - Stay Off
				 2  - Restore Previous State
				 3  - Turn On
				 Default value is turnon(3)."
			::= { system 8 }  	


		hostName OBJECT-TYPE
			SYNTAX DisplayString
			MAX-ACCESS read-write
			STATUS current
			DESCRIPTION
				"The host name between 1 to 64 characters.
				Supported characters: 0-9 a-z A-Z - ('-' is not allowed to be the first/last character).
				Default value is huawei."
			::= { system 9 } 			
					           

		systemGuid OBJECT-TYPE
			SYNTAX DisplayString
			MAX-ACCESS read-only
			STATUS current
			DESCRIPTION
				"The GUID is hex string such as 
				********-****-****-****-************."
			::= { system 10 }  
			

		identify OBJECT-TYPE   
			SYNTAX DisplayString
			MAX-ACCESS read-write
			STATUS current
			DESCRIPTION
				"identify use to control on or off of led. 
				 identify mode:   
				 0  - Off	
				 1  - Temporary On	
				 2  - Force Identify On	             
				 
				 set format: <mode>,[ontime]
				 get format: <mode>   
				 
				 When <mode> = 0 or <mode> = 2,
				 the format is only <mode>.
				    
				 [ontime] is option and value is in [1,255],
				 When set Temporary On without [ontime],
				 The default Temporary On time are 15 seconds."
			::= { system 11 }
								

		systemPowerState OBJECT-TYPE   
			SYNTAX INTEGER
				{
				normalPowerOff(1),
				powerOn(2),				
				forcedSystemReset(3),
				forcedPowerCycle(4),
				forcedPowerOff(5)
				}
			MAX-ACCESS read-write
			STATUS current
			DESCRIPTION
				"System Power Status Get.
				1  - Power Off
				2  - Power On
				System Power Status Set.
				1  - Normal Power Off
				2  - Power On
				3  - Forced System Reset
				4  - Forced Power Cycle
				5  - Forced Power Off
				The set actions are a process which will take effect in a while. 
				When system in poweroff state, Power Off/Reset/PowerOffThenOn commonds are not supported."
			::= { system 12 }
		

		presentSystemPower OBJECT-TYPE
			SYNTAX INTEGER
			MAX-ACCESS read-only
			STATUS current
			DESCRIPTION
				"Display the present system power."
			::= { system 13 } 	 

		deviceOwnerID OBJECT-TYPE
			SYNTAX DisplayString
			MAX-ACCESS read-only
			STATUS current
			DESCRIPTION
				"The device owner ID, maxlength  is 64 characters."
			::= { system 14 } 
		
		deviceslotID OBJECT-TYPE
			SYNTAX DisplayString
			MAX-ACCESS read-only
			STATUS current
			DESCRIPTION
				"The device slot ID of a server exists, the value ranges from 1 to 80. Otherwise, the value is 0."
			::= { system 15 } 
			
		remoteOEMInfo OBJECT-TYPE
			SYNTAX DisplayString
			MAX-ACCESS read-write
			STATUS current
			DESCRIPTION
				"The remoteOEMinfo, maxlength  is 255 characters."
			::= { system 16 } 			
			
		deviceLocationInfo OBJECT-TYPE
			SYNTAX DisplayString
			MAX-ACCESS read-write
			STATUS current
			DESCRIPTION
				"The deviceLocationInfo between 0 and 64 characters.
				Default value is server room."
			::= { system 17 }
		
		deviceRemoteManageID OBJECT-TYPE
			SYNTAX DisplayString
			MAX-ACCESS read-write
			STATUS current
			DESCRIPTION
				"The deviceRemoteManageID between 0 and 64 characters."
			::= { system 18 }			
			
		bmcReboot OBJECT-TYPE
			SYNTAX INTEGER
			        {
			        reboot(1)
			        }			   
			MAX-ACCESS read-write
			STATUS current
			DESCRIPTION
				"Reboot the BMC management system.When set, the value is only 1, write only."
			::= { system 19 }			
			
		powerOnPermit OBJECT-TYPE
			SYNTAX INTEGER
			{
				notPermit(1),
				permit(2)
			}
			MAX-ACCESS read-write
			STATUS current
			DESCRIPTION
				"Set power on permission. notPermit 1, permit 2."
			::= { system 20 }
			
		autoDiscoveryEnable OBJECT-TYPE
			SYNTAX INTEGER
			{
				disable(1),
				enable(2)
			}
			MAX-ACCESS read-write
			STATUS current
			DESCRIPTION
				"Auto discovery state. disable 1, enable 2.
				Default value is disable(1)."
			::= { system 21 }
		
		productUniqueID OBJECT-TYPE
			SYNTAX DisplayString
			MAX-ACCESS read-only
			STATUS current
			DESCRIPTION
				"The productUniqueID is hex string."
			::= { system 22 }
		systemCpuUsage OBJECT-TYPE
			SYNTAX INTEGER
			MAX-ACCESS read-only
			STATUS current
			DESCRIPTION
				"Percent of CPU usage.
				The value defined as:
				-1: invalid current CPU usage.
				[0,100]: represents the current CPU usage.
				NOTE:
				If iBMA 2.0 has been installed and started on the OS, iBMA 2.0 provides the CPU usage data, which is consistent with that collected by the OS.
				If iBMA 2.0 is not installed or started, the Intel management Engine (ME) provides the CPU usage data, which is compute utilization per second of all cores calculated by CPU internal modules."
			::= { system 23 }
			
		systemBootOnce OBJECT-TYPE
			SYNTAX INTEGER
			{
				once(1),
				permanent(2)
			}
			MAX-ACCESS read-write
			STATUS current
			DESCRIPTION
			"System boot once or permanent. once 1, permanent 2.
			Default value is once(1)."
			::= { system 24 }

		systemMemUsage OBJECT-TYPE
			SYNTAX INTEGER
			MAX-ACCESS read-only
			STATUS current
			DESCRIPTION
				"Percent of memory usage.
				The value defined as:
				-1: invalid current memory usage.
				[0,100]: represents the current memory usage.
				NOTE:
				If iBMA 2.0 has been installed and started on the OS, iBMA 2.0 provides the memory usage data, which is consistent with that collected by the OS.
				If iBMA 2.0 is not installed or started, the Intel management Engine (ME) provides the memory bandwidth usage, which is different from the memory usage collected by the OS."
			::= { system 25 }	
		systemCpuUsageThre OBJECT-TYPE
			SYNTAX INTEGER
			MAX-ACCESS read-write
			STATUS current
			DESCRIPTION
				"Percent of CPU usage threshold.
				This value is in [0,100]."
			::= { system 26 }
		systemMemUsageThre OBJECT-TYPE
			SYNTAX INTEGER
			MAX-ACCESS read-write
			STATUS current
			DESCRIPTION
				"Percent of memory usage threshold.
				This value is in [0,100]."
			::= { system 27 }
		systemDiskPartitionUsageThre OBJECT-TYPE
			SYNTAX INTEGER
			MAX-ACCESS read-write
			STATUS current
			DESCRIPTION
				"Percent of hard disk partition usage threshold.
				This value is in [0,100]."
			::= { system 28 }	
			
		systemTimeZoneStr OBJECT-TYPE
			SYNTAX DisplayString
			MAX-ACCESS read-write
			STATUS current
			DESCRIPTION
				"systemTimeZone information about iBMC time zone.
				The value can be time-offset : GMT-12:00~GMT+14:00 e.g. GMT+08:00,GMT-04:30.
				The value can be city name , e.g. Asia/Shanghai,America/New_York."
			::= { system 29 }
				
--    ****** systemHealthEvent Information *******************************
  
--	  systemHealthEvent OBJECT IDENTIFIER ::= { system 30 }    

		systemHealthEventDescriptionTable OBJECT-TYPE
			SYNTAX SEQUENCE OF SystemHealthEventDescriptionEntry 
			MAX-ACCESS not-accessible
			STATUS current
			DESCRIPTION
				"A table containing the part component."
			::= { system 50 }
        
                systemHealthEventDescriptionEntry OBJECT-TYPE
			SYNTAX SystemHealthEventDescriptionEntry 
			MAX-ACCESS not-accessible
			STATUS current
			DESCRIPTION
				"."
			INDEX { eventIndex }
			::= { systemHealthEventDescriptionTable 1 }
		
		SystemHealthEventDescriptionEntry ::=
			SEQUENCE {
				eventIndex
					INTEGER, 
				eventSensorName
					DisplayString,
				eventAlertTime
					DisplayString,
				eventAlertSeverity
					INTEGER,	
				eventDescription 
					DisplayString,
				eventCode
					DisplayString,
				eventOID
					OBJECT IDENTIFIER,
				newEventCode
					DisplayString,
				newEventOID
					OBJECT IDENTIFIER
					}
				 

		eventIndex OBJECT-TYPE	
			SYNTAX INTEGER
			MAX-ACCESS not-accessible
			STATUS current
			DESCRIPTION
				"Information about event id."
			::= { systemHealthEventDescriptionEntry 1 }    
			

		eventSensorName OBJECT-TYPE
			SYNTAX DisplayString
			MAX-ACCESS read-only
			STATUS current
			DESCRIPTION
				"The sensor name between 1 to 16 characters."
			::= { systemHealthEventDescriptionEntry 2 }
			

		eventAlertTime OBJECT-TYPE
			SYNTAX DisplayString
			MAX-ACCESS read-only
			STATUS current
			DESCRIPTION
				"The format of alert time is yyyy-mm-dd hh:mm:ss, based on UTC."
			::= { systemHealthEventDescriptionEntry 3 }


		eventAlertSeverity OBJECT-TYPE
			SYNTAX INTEGER
				{
				ok(1),
				minor(2),
				major(3),
				critical(4)
				}
			MAX-ACCESS read-only
			STATUS current
			DESCRIPTION
				"The information about event level."
			::= { systemHealthEventDescriptionEntry 4 }     
			

		eventDescription OBJECT-TYPE
			SYNTAX DisplayString
			MAX-ACCESS read-only
			STATUS current
			DESCRIPTION
				"The event description between 1 to 255 characters."
			::= { systemHealthEventDescriptionEntry 5 }		
            
		eventCode OBJECT-TYPE	
			SYNTAX DisplayString
			MAX-ACCESS not-accessible
			STATUS current
			DESCRIPTION
				"The information about event code."
			::= { systemHealthEventDescriptionEntry 6 }    

		eventOID OBJECT-TYPE
			SYNTAX OBJECT IDENTIFIER
			MAX-ACCESS read-only
			STATUS current
			DESCRIPTION
				"The object identification of current event."
			::= { systemHealthEventDescriptionEntry 7 }				
		newEventCode OBJECT-TYPE	
			SYNTAX DisplayString
			MAX-ACCESS not-accessible
			STATUS current
			DESCRIPTION
				"The information about new event code."
			::= { systemHealthEventDescriptionEntry 8 }    

		newEventOID OBJECT-TYPE
			SYNTAX OBJECT IDENTIFIER
			MAX-ACCESS read-only
			STATUS current
			DESCRIPTION
				"The new object identification of current event."
			::= { systemHealthEventDescriptionEntry 9 }		
--    ****** DNS Location *******************************
  --	  systemDiskPartition OBJECT IDENTIFIER ::= { system 51 }    

		systemDiskPartitionTable OBJECT-TYPE
			SYNTAX SEQUENCE OF SystemDiskPartitionEntry 
			MAX-ACCESS not-accessible
			STATUS current
			DESCRIPTION
				"A table containing the hard disk partition information."
			::= { system  51 }
        
		systemDiskPartitionEntry OBJECT-TYPE
			SYNTAX SystemDiskPartitionEntry 
			MAX-ACCESS not-accessible
			STATUS current
			DESCRIPTION
				"."
			INDEX { diskPartitionIndex }
			::= { systemDiskPartitionTable 1 }
		
		SystemDiskPartitionEntry ::=
			SEQUENCE {
				diskPartitionIndex
					INTEGER, 
				diskPartitionName
					DisplayString,
				totalCapacityGiB
					DisplayString,	
				diskPartitionUsage 
					INTEGER
					}
				 
		diskPartitionIndex OBJECT-TYPE	
			SYNTAX INTEGER
			MAX-ACCESS not-accessible
			STATUS current
			DESCRIPTION
				"Information about hard disk Partition Index."
			::= { systemDiskPartitionEntry 1 }    
			
		diskPartitionName OBJECT-TYPE
			SYNTAX DisplayString
			MAX-ACCESS read-only
			STATUS current
			DESCRIPTION
				"The hard disk partition name between 1 to 64 characters."
			::= { systemDiskPartitionEntry 2 }
			
		totalCapacityGiB OBJECT-TYPE
			SYNTAX DisplayString
			MAX-ACCESS read-only
			STATUS current
			DESCRIPTION
				"The hard disk partition total capactity, unit GB."
			::= { systemDiskPartitionEntry 3 }

		diskPartitionUsage OBJECT-TYPE
			SYNTAX INTEGER
			MAX-ACCESS read-only
			STATUS current
			DESCRIPTION
				"The usage of hard disk partion."
			::= { systemDiskPartitionEntry 4 }			 				
			
--    ****** DNS Location *******************************		

		domainNameSystem OBJECT IDENTIFIER ::= { hwiBMC 2 }    


		domainName OBJECT-TYPE	
			SYNTAX DisplayString
			MAX-ACCESS read-write
			STATUS current
			DESCRIPTION
				"Domain Name between 0 to 67  characters.
				A domain name supports all characters except space,double quotation,equal and the following characters:#'&."
			::= { domainNameSystem 1 } 
			

		preferredDNSServer OBJECT-TYPE
			SYNTAX DisplayString
			MAX-ACCESS read-write
			STATUS current
			DESCRIPTION
				"Preferred DNS server IPv4 address.
				 this value is right IPv4 address or empty, 
				 the default value is empty."
			::= { domainNameSystem 2 }
			

		alternateDNSServer OBJECT-TYPE
			SYNTAX DisplayString
			MAX-ACCESS read-write
			STATUS current
			DESCRIPTION
				"Alternate DNS server IPv4 address.
				 this value is right IPv4 address or empty, 
				 the default value is empty."
			::= { domainNameSystem 3 }
			

		dnsSource OBJECT-TYPE
			SYNTAX INTEGER
				{
				manual (1),
				auto (2)
				}
			MAX-ACCESS read-write
			STATUS current
			DESCRIPTION
				"Information about DNS source."
			::= { domainNameSystem 4 }
			

		bindNetPort OBJECT-TYPE
			SYNTAX INTEGER
				{
				eth0 (1),
				eth1 (2)
				}
			MAX-ACCESS read-write
			STATUS obsolete
			DESCRIPTION
				"Information about DNS bind net port."
			::= { domainNameSystem 5 }
			

		bindIPProtocol OBJECT-TYPE
			SYNTAX INTEGER
				{
				ipv4 (1),
				ipv6 (2)
				}
			MAX-ACCESS read-write
			STATUS current
			DESCRIPTION
				"Information about DNS bind ip protocol."
			::= { domainNameSystem 6 }
		
                               
--    ****** LDAP Location *******************************  
		ldap  OBJECT IDENTIFIER ::= { hwiBMC 3 }                                

  		ldapEnable OBJECT-TYPE
			SYNTAX INTEGER
			{
				disable (1),
				enable (2)				
			}
			MAX-ACCESS read-write
			STATUS current
			DESCRIPTION
				"The state of LDAP. 
				Default value is disable(1)."
			::= { ldap 1 }
		
		ldapDomainServer1 OBJECT-TYPE
			SYNTAX DisplayString
			MAX-ACCESS read-write
			STATUS current
			DESCRIPTION
				"LDAP domain server between 1 to 255 characters.
				Default value is 0.0.0.0. Max length is 255 characters."
			::= { ldap 2 } 
			
		ldapUserDomain1 OBJECT-TYPE
			SYNTAX DisplayString
			MAX-ACCESS read-write
			STATUS current
			DESCRIPTION   
				"LDAP user domain if the string consists of numbers, letters, and special characters, the maximum length is 255 characters.
				E.g. CN=employee,OU=company,DC=ldap,DC=ibmc,DC=com or OU=department,OU=company,DC=ldap,DC=ibmc."
			::= { ldap 3 }
			
		ldapPort1 OBJECT-TYPE
			SYNTAX INTEGER
			MAX-ACCESS read-write
			STATUS current
			DESCRIPTION   
				"Specifies the port number for the LDAP service.
				Value: an integer ranging from 1 to 65535
				The default value is 636."
			::= { ldap 4 }
			
		ldapDomainServer2 OBJECT-TYPE
			SYNTAX DisplayString
			MAX-ACCESS read-write
			STATUS current
			DESCRIPTION
				"LDAP domain server between 1 to 255 characters.
				Default value is 0.0.0.0. Max length is 255 characters."
			::= { ldap 5 } 
			
		ldapUserDomain2 OBJECT-TYPE
			SYNTAX DisplayString
			MAX-ACCESS read-write
			STATUS current
			DESCRIPTION   
				"LDAP user domain if the string consists of numbers, letters, and special characters, the maximum length is 255 characters.
				E.g. CN=employee,OU=company,DC=ldap,DC=ibmc,DC=com or OU=department,OU=company,DC=ldap,DC=ibmc."
			::= { ldap 6 }
			
		ldapPort2 OBJECT-TYPE
			SYNTAX INTEGER
			MAX-ACCESS read-write
			STATUS current
			DESCRIPTION   
				"Specifies the port number for the LDAP service.
				Value: an integer ranging from 1 to 65535
				The default value is 636."
			::= { ldap 7 }
		
		ldapDomainServer3 OBJECT-TYPE
			SYNTAX DisplayString
			MAX-ACCESS read-write
			STATUS current
			DESCRIPTION
				"LDAP domain server between 1 to 255 characters.
				Default value is 0.0.0.0. Max length is 255 characters."
			::= { ldap 8 } 
			
		ldapUserDomain3 OBJECT-TYPE
			SYNTAX DisplayString
			MAX-ACCESS read-write
			STATUS current
			DESCRIPTION   
				"LDAP user domain if the string consists of numbers, letters, and special characters, the maximum length is 255 characters.
				E.g. CN=employee,OU=company,DC=ldap,DC=ibmc,DC=com or OU=department,OU=company,DC=ldap,DC=ibmc."
			::= { ldap 9 }
			
		ldapPort3 OBJECT-TYPE
			SYNTAX INTEGER
			MAX-ACCESS read-write
			STATUS current
			DESCRIPTION   
				"Specifies the port number for the LDAP service.
				Value: an integer ranging from 1 to 65535
				The default value is 636."
			::= { ldap 10 }   
			
		ldapDomainServer4 OBJECT-TYPE
			SYNTAX DisplayString
			MAX-ACCESS read-write
			STATUS current
			DESCRIPTION
				"LDAP domain server between 1 to 255 characters.
				Default value is 0.0.0.0. Max length is 255 characters."
			::= { ldap 11 } 
			
		ldapUserDomain4 OBJECT-TYPE
			SYNTAX DisplayString
			MAX-ACCESS read-write
			STATUS current
			DESCRIPTION   
				"LDAP user domain if the string consists of numbers, letters, and special characters, the maximum length is 255 characters.
				E.g. CN=employee,OU=company,DC=ldap,DC=ibmc,DC=com or OU=department,OU=company,DC=ldap,DC=ibmc."
			::= { ldap 12 }
			
		ldapPort4 OBJECT-TYPE
			SYNTAX INTEGER
			MAX-ACCESS read-write
			STATUS current
			DESCRIPTION   
				"Specifies the port number for the LDAP service.
				Value: an integer ranging from 1 to 65535
				The default value is 636."
			::= { ldap 13 }    
			
		ldapDomainServer5 OBJECT-TYPE
			SYNTAX DisplayString
			MAX-ACCESS read-write
			STATUS current
			DESCRIPTION
				"LDAP domain server between 1 to 255 characters.
				Default value is 0.0.0.0. Max length is 255 characters."
			::= { ldap 14 } 
			
		ldapUserDomain5 OBJECT-TYPE
			SYNTAX DisplayString
			MAX-ACCESS read-write
			STATUS current
			DESCRIPTION   
				"LDAP user domain if the string consists of numbers, letters, and special characters, the maximum length is 255 characters..
				E.g. CN=employee,OU=company,DC=ldap,DC=ibmc,DC=com or OU=department,OU=company,DC=ldap,DC=ibmc."
			::= { ldap 15 }
			
		ldapPort5 OBJECT-TYPE
			SYNTAX INTEGER
			MAX-ACCESS read-write
			STATUS current
			DESCRIPTION   
				"Specifies the port number for the LDAP service.
				Value: an integer ranging from 1 to 65535
				The default value is 636."
			::= { ldap 16 }    
			
		ldapDomainServer6 OBJECT-TYPE
			SYNTAX DisplayString
			MAX-ACCESS read-write
			STATUS current
			DESCRIPTION
				"LDAP domain server between 1 to 255 characters.
				Default value is 0.0.0.0. Max length is 255 characters."
			::= { ldap 17 } 
			
		ldapUserDomain6 OBJECT-TYPE
			SYNTAX DisplayString
			MAX-ACCESS read-write
			STATUS current
			DESCRIPTION   
				"LDAP user domain if the string consists of numbers, letters, and special characters, the maximum length is 255 characters.
				E.g. CN=employee,OU=company,DC=ldap,DC=ibmc,DC=com or OU=department,OU=company,DC=ldap,DC=ibmc."
			::= { ldap 18 }
			
		ldapPort6 OBJECT-TYPE
			SYNTAX INTEGER
			MAX-ACCESS read-write
			STATUS current
			DESCRIPTION   
				"Specifies the port number for the LDAP service.
				Value: an integer ranging from 1 to 65535
				The default value is 636."
			::= { ldap 19 }
			
		ldapGroupInfoDescription1Table OBJECT-TYPE
			SYNTAX SEQUENCE OF LDAPGroupInfoDescription1Entry 
			MAX-ACCESS not-accessible
			STATUS current
			DESCRIPTION
				"A table containing the list of LDAP information."
			::= { ldap 50 }
        
		ldapGroupInfoDescription1Entry OBJECT-TYPE
			SYNTAX LDAPGroupInfoDescription1Entry  
			MAX-ACCESS not-accessible
			STATUS current
			DESCRIPTION
				"."
			INDEX { groupIndex }
			::= { ldapGroupInfoDescription1Table 1 }
		
		LDAPGroupInfoDescription1Entry ::=
			SEQUENCE {
				groupIndex
					INTEGER, 
				groupName
					DisplayString, 
				groupDomain
					DisplayString,
				groupPrivilege 
					INTEGER,
				groupInterfaces
				    INTEGER
				}  
				

		groupIndex OBJECT-TYPE	
			SYNTAX INTEGER
			MAX-ACCESS not-accessible
			STATUS current
			DESCRIPTION
				"LDAP group index."
			::= { ldapGroupInfoDescription1Entry 1 } 
				

		groupName OBJECT-TYPE	
			SYNTAX DisplayString
			MAX-ACCESS read-write
			STATUS current
			DESCRIPTION
				"LDAP group name if the string consists of numbers, letters, and special characters, the maximum length is 255 characters."
			::= { ldapGroupInfoDescription1Entry 2 } 
			

		groupDomain OBJECT-TYPE
			SYNTAX DisplayString
			MAX-ACCESS read-write
			STATUS current
			DESCRIPTION
				"LDAP group domain if the string consists of numbers, letters, and special characters, the maximum length is 255 characters.
				E.g. Group0 CN=group0,DC=ldap,DC=ibmc,DC=com."
			::= { ldapGroupInfoDescription1Entry 3 }   
			

		groupPrivilege OBJECT-TYPE
			SYNTAX INTEGER
			{
				commonUser(1),
				noAccess(0),
				operator(2),	
				administrator(3),
				customRole1(4),
				customRole2(5),
				customRole3(6),
				customRole4(7)
			}	
			MAX-ACCESS read-write
			STATUS current
			DESCRIPTION
				"0 - no access
				 1 - common user
				 2 - operator 
				 3 - administrator
				 4 - custom role1
				 5 - custom role2
				 6 - custom role3
				 7 - custom role4
				 Default value is commonUser(1)."
			::= { ldapGroupInfoDescription1Entry 4 } 
			
		groupInterfaces OBJECT-TYPE
			SYNTAX INTEGER
			MAX-ACCESS read-write
			STATUS current
			DESCRIPTION
				"Information about LDAP group login interfaces.
				bit0 - Web:      0 disabled; 1 enabled
				bit3 - SSH:      0 disabled; 1 enabled
				bit7 - Redfish:  0 disabled; 1 enabled"
			::= { ldapGroupInfoDescription1Entry 5 }

		ldapGroupInfoDescription2Table OBJECT-TYPE
			SYNTAX SEQUENCE OF LDAPGroupInfoDescription2Entry 
			MAX-ACCESS not-accessible
			STATUS current
			DESCRIPTION
				"A table containing the list of LDAP information."
			::= { ldap 51 }
        
		ldapGroupInfoDescription2Entry OBJECT-TYPE
			SYNTAX LDAPGroupInfoDescription2Entry  
			MAX-ACCESS not-accessible
			STATUS current
			DESCRIPTION
				"."
			INDEX { groupIndex2 }
			::= { ldapGroupInfoDescription2Table 1 }
		
		LDAPGroupInfoDescription2Entry ::=
			SEQUENCE {
				groupIndex2
					INTEGER, 
				groupName2
					DisplayString,		
				groupPrivilege2 
					INTEGER,
				groupInterfaces2
				    INTEGER,
				groupDomain2
					DisplayString
				}  
				

		groupIndex2 OBJECT-TYPE	
			SYNTAX INTEGER
			MAX-ACCESS not-accessible
			STATUS current
			DESCRIPTION
				"LDAP group index."
			::= { ldapGroupInfoDescription2Entry 1 } 
				

		groupName2 OBJECT-TYPE	
			SYNTAX DisplayString
			MAX-ACCESS read-write
			STATUS current
			DESCRIPTION
				"LDAP group name if the string consists of numbers, letters, and special characters, the maximum length is 255 characters."
			::= { ldapGroupInfoDescription2Entry 2 } 

		groupPrivilege2 OBJECT-TYPE
			SYNTAX INTEGER
			{
				commonUser(1),
				noAccess(0),
				operator(2),	
				administrator(3),
				customRole1(4),
				customRole2(5),
				customRole3(6),
				customRole4(7)
			}	
			MAX-ACCESS read-write
			STATUS current
			DESCRIPTION
				"0 - no access
				 1 - common user
				 2 - operator 
				 3 - administrator
				 4 - custom role1
				 5 - custom role2
				 6 - custom role3
				 7 - custom role4
				 Default value is commonUser(1)."
			::= { ldapGroupInfoDescription2Entry 3 }  
			
		groupInterfaces2 OBJECT-TYPE
			SYNTAX INTEGER
			MAX-ACCESS read-write
			STATUS current
			DESCRIPTION
				"Information about LDAP group login interfaces.
				bit0 - Web:      0 disabled; 1 enabled
				bit3 - SSH:      0 disabled; 1 enabled
				bit7 - Redfish:  0 disabled; 1 enabled"
			::= { ldapGroupInfoDescription2Entry 4 }
			
		groupDomain2 OBJECT-TYPE
			SYNTAX DisplayString
			MAX-ACCESS read-write
			STATUS current
			DESCRIPTION
				"LDAP group domain if the string consists of numbers, letters, and special characters, the maximum length is 255 characters.
				E.g. Group0 CN=group0,DC=ldap,DC=ibmc,DC=com."
			::= { ldapGroupInfoDescription2Entry 5 }  
			
		ldapGroupInfoDescription3Table OBJECT-TYPE
			SYNTAX SEQUENCE OF LDAPGroupInfoDescription3Entry 
			MAX-ACCESS not-accessible
			STATUS current
			DESCRIPTION
				"A table containing the list of LDAP information."
			::= { ldap 52 }
        
		ldapGroupInfoDescription3Entry OBJECT-TYPE
			SYNTAX LDAPGroupInfoDescription3Entry  
			MAX-ACCESS not-accessible
			STATUS current
			DESCRIPTION
				"."
			INDEX { groupIndex3 }
			::= { ldapGroupInfoDescription3Table 1 }
		
		LDAPGroupInfoDescription3Entry ::=
			SEQUENCE {
				groupIndex3
					INTEGER, 
				groupName3
					DisplayString, 
				groupPrivilege3 
					INTEGER,
				groupInterfaces3
				    INTEGER,
				groupDomain3
					DisplayString
				}  
				

		groupIndex3 OBJECT-TYPE	
			SYNTAX INTEGER
			MAX-ACCESS not-accessible
			STATUS current
			DESCRIPTION
				"LDAP group index."
			::= { ldapGroupInfoDescription3Entry 1 } 
				

		groupName3 OBJECT-TYPE	
			SYNTAX DisplayString
			MAX-ACCESS read-write
			STATUS current
			DESCRIPTION
				"LDAP group name if the string consists of numbers, letters, and special characters, the maximum length is 255 characters."
			::= { ldapGroupInfoDescription3Entry 2 } 

		groupPrivilege3 OBJECT-TYPE
			SYNTAX INTEGER
			{
				commonUser(1),
				noAccess(0),
				operator(2),	
				administrator(3),
				customRole1(4),
				customRole2(5),
				customRole3(6),
				customRole4(7)
			}	
			MAX-ACCESS read-write
			STATUS current
			DESCRIPTION
				"0 - no access
				 1 - common user
				 2 - operator 
				 3 - administrator
				 4 - custom role1
				 5 - custom role2
				 6 - custom role3
				 7 - custom role4
				 Default value is commonUser(1)."
			::= { ldapGroupInfoDescription3Entry 3 }  	
			
		groupInterfaces3 OBJECT-TYPE
			SYNTAX INTEGER
			MAX-ACCESS read-write
			STATUS current
			DESCRIPTION
				"Information about LDAP group login interfaces.
				bit0 - Web:      0 disabled; 1 enabled
				bit3 - SSH:      0 disabled; 1 enabled
				bit7 - Redfish:  0 disabled; 1 enabled"
			::= { ldapGroupInfoDescription3Entry 4 }
			
		groupDomain3 OBJECT-TYPE
			SYNTAX DisplayString
			MAX-ACCESS read-write
			STATUS current
			DESCRIPTION
				"LDAP group domain if the string consists of numbers, letters, and special characters, the maximum length is 255 characters.
				E.g. Group0 CN=group0,DC=ldap,DC=ibmc,DC=com."
			::= { ldapGroupInfoDescription3Entry 5 } 
			     
		ldapGroupInfoDescription4Table OBJECT-TYPE
			SYNTAX SEQUENCE OF LDAPGroupInfoDescription4Entry 
			MAX-ACCESS not-accessible
			STATUS current
			DESCRIPTION
				"A table containing the list of LDAP information."
			::= { ldap 53 }

		ldapGroupInfoDescription4Entry OBJECT-TYPE
			SYNTAX LDAPGroupInfoDescription4Entry  
			MAX-ACCESS not-accessible
			STATUS current
			DESCRIPTION
				"."
			INDEX { groupIndex4 }
			::= { ldapGroupInfoDescription4Table 1 }
		
		LDAPGroupInfoDescription4Entry ::=
			SEQUENCE {
				groupIndex4
					INTEGER, 
				groupName4
					DisplayString, 
				groupPrivilege4 
					INTEGER,
				groupInterfaces4
				    INTEGER,
				groupDomain4
					DisplayString
				}  
				

		groupIndex4 OBJECT-TYPE	
			SYNTAX INTEGER
			MAX-ACCESS not-accessible
			STATUS current
			DESCRIPTION
				"LDAP group index."
			::= { ldapGroupInfoDescription4Entry 1 } 
				

		groupName4 OBJECT-TYPE	
			SYNTAX DisplayString
			MAX-ACCESS read-write
			STATUS current
			DESCRIPTION
				"LDAP group name if the string consists of numbers, letters, and special characters, the maximum length is 255 characters."
			::= { ldapGroupInfoDescription4Entry 2 } 

		groupPrivilege4 OBJECT-TYPE
			SYNTAX INTEGER
			{
				commonUser(1),
				noAccess(0),
				operator(2),	
				administrator(3),
				customRole1(4),
				customRole2(5),
				customRole3(6),
				customRole4(7)
			}	
			MAX-ACCESS read-write
			STATUS current
			DESCRIPTION
				"0 - no access
				 1 - common user
				 2 - operator 
				 3 - administrator
				 4 - custom role1
				 5 - custom role2
				 6 - custom role3
				 7 - custom role4
				 Default value is commonUser(1)."
			::= { ldapGroupInfoDescription4Entry 3 }  	
			
		groupInterfaces4 OBJECT-TYPE
			SYNTAX INTEGER
			MAX-ACCESS read-write
			STATUS current
			DESCRIPTION
				"Information about LDAP group login interfaces.
				bit0 - Web:      0 disabled; 1 enabled
				bit3 - SSH:      0 disabled; 1 enabled
				bit7 - Redfish:  0 disabled; 1 enabled"
			::= { ldapGroupInfoDescription4Entry 4 }
			
		groupDomain4 OBJECT-TYPE
			SYNTAX DisplayString
			MAX-ACCESS read-write
			STATUS current
			DESCRIPTION
				"LDAP group domain if the string consists of numbers, letters, and special characters, the maximum length is 255 characters.
				E.g. Group0 CN=group0,DC=ldap,DC=ibmc,DC=com."
			::= { ldapGroupInfoDescription4Entry 5 }
			
		ldapGroupInfoDescription5Table OBJECT-TYPE
			SYNTAX SEQUENCE OF LDAPGroupInfoDescription5Entry 
			MAX-ACCESS not-accessible
			STATUS current
			DESCRIPTION
				"A table containing the list of LDAP information."
			::= { ldap 54 }
	
		ldapGroupInfoDescription5Entry OBJECT-TYPE
			SYNTAX LDAPGroupInfoDescription5Entry  
			MAX-ACCESS not-accessible
			STATUS current
			DESCRIPTION
				"."
			INDEX { groupIndex5 }
			::= { ldapGroupInfoDescription5Table 1 }
		
		LDAPGroupInfoDescription5Entry ::=
			SEQUENCE {
				groupIndex5
					INTEGER, 
				groupName5
					DisplayString, 
				groupPrivilege5 
					INTEGER,
				groupInterfaces5
				    INTEGER,
				groupDomain5
					DisplayString
				}  
				

		groupIndex5 OBJECT-TYPE	
			SYNTAX INTEGER
			MAX-ACCESS not-accessible
			STATUS current
			DESCRIPTION
				"LDAP group index."
			::= { ldapGroupInfoDescription5Entry 1 } 
				

		groupName5 OBJECT-TYPE	
			SYNTAX DisplayString
			MAX-ACCESS read-write
			STATUS current
			DESCRIPTION
				"LDAP group name if the string consists of numbers, letters, and special characters, the maximum length is 255 characters."
			::= { ldapGroupInfoDescription5Entry 2 } 

		groupPrivilege5 OBJECT-TYPE
			SYNTAX INTEGER
			{
				commonUser(1),
				noAccess(0),
				operator(2),	
				administrator(3),
				customRole1(4),
				customRole2(5),
				customRole3(6),
				customRole4(7)
			}	
			MAX-ACCESS read-write
			STATUS current
			DESCRIPTION
				"0 - no access
				 1 - common user
				 2 - operator 
				 3 - administrator
				 4 - custom role1
				 5 - custom role2
				 6 - custom role3
				 7 - custom role4
				 Default value is commonUser(1)."
			::= { ldapGroupInfoDescription5Entry 3 }  	
			
		groupInterfaces5 OBJECT-TYPE
			SYNTAX INTEGER
			MAX-ACCESS read-write
			STATUS current
			DESCRIPTION
				"Information about LDAP group login interfaces.
				bit0 - Web:      0 disabled; 1 enabled
				bit3 - SSH:      0 disabled; 1 enabled
				bit7 - Redfish:  0 disabled; 1 enabled"
			::= { ldapGroupInfoDescription5Entry 4 }
			
		groupDomain5 OBJECT-TYPE
			SYNTAX DisplayString
			MAX-ACCESS read-write
			STATUS current
			DESCRIPTION
				"LDAP group domain if the string consists of numbers, letters, and special characters, the maximum length is 255 characters.
				E.g. Group0 CN=group0,DC=ldap,DC=ibmc,DC=com."
			::= { ldapGroupInfoDescription5Entry 5 }
		
		ldapGroupInfoDescription6Table OBJECT-TYPE
			SYNTAX SEQUENCE OF LDAPGroupInfoDescription6Entry 
			MAX-ACCESS not-accessible
			STATUS current
			DESCRIPTION
				"A table containing the list of LDAP information."
			::= { ldap 55 }

		ldapGroupInfoDescription6Entry OBJECT-TYPE
			SYNTAX LDAPGroupInfoDescription6Entry  
			MAX-ACCESS not-accessible
			STATUS current
			DESCRIPTION
				"."
			INDEX { groupIndex6 }
			::= { ldapGroupInfoDescription6Table 1 }
		
		LDAPGroupInfoDescription6Entry ::=
			SEQUENCE {
				groupIndex6
					INTEGER, 
				groupName6
					DisplayString, 
				groupPrivilege6 
					INTEGER,
				groupInterfaces6
				    INTEGER,
				groupDomain6
					DisplayString
				}  
				

		groupIndex6 OBJECT-TYPE	
			SYNTAX INTEGER
			MAX-ACCESS not-accessible
			STATUS current
			DESCRIPTION
				"LDAP group index."
			::= { ldapGroupInfoDescription6Entry 1 } 
				

		groupName6 OBJECT-TYPE	
			SYNTAX DisplayString
			MAX-ACCESS read-write
			STATUS current
			DESCRIPTION
				"LDAP group name if the string consists of numbers, letters, and special characters, the maximum length is 255 characters."
			::= { ldapGroupInfoDescription6Entry 2 } 

		groupPrivilege6 OBJECT-TYPE
			SYNTAX INTEGER
			{
				commonUser(1),
				noAccess(0),
				operator(2),	
				administrator(3),
				customRole1(4),
				customRole2(5),
				customRole3(6),
				customRole4(7)
			}	
			MAX-ACCESS read-write
			STATUS current
			DESCRIPTION
				"0 - no access
				 1 - common user
				 2 - operator 
				 3 - administrator
				 4 - custom role1
				 5 - custom role2
				 6 - custom role3
				 7 - custom role4
				 Default value is commonUser(1)."
			::= { ldapGroupInfoDescription6Entry 3 }  	
			
		groupInterfaces6 OBJECT-TYPE
			SYNTAX INTEGER
			MAX-ACCESS read-write
			STATUS current
			DESCRIPTION
				"Information about LDAP group login interfaces.
				bit0 - Web:      0 disabled; 1 enabled
				bit3 - SSH:      0 disabled; 1 enabled
				bit7 - Redfish:  0 disabled; 1 enabled"
			::= { ldapGroupInfoDescription6Entry 4 }
			
		groupDomain6 OBJECT-TYPE
			SYNTAX DisplayString
			MAX-ACCESS read-write
			STATUS current
			DESCRIPTION
				"LDAP group domain if the string consists of numbers, letters, and special characters, the maximum length is 255 characters.
				E.g. Group0 CN=group0,DC=ldap,DC=ibmc,DC=com."
			::= { ldapGroupInfoDescription6Entry 5 }
--    ****** Trap Location *******************************  			

		trap  OBJECT IDENTIFIER ::= { hwiBMC 4 }                                
        

  		trapEnable OBJECT-TYPE
			SYNTAX INTEGER
					{
					disable (1),
					enable (2)				
					}
			MAX-ACCESS read-write
			STATUS current
			DESCRIPTION
				"The state of Trap. 
				Default value is enable(2)."
			::= { trap 1 }
		 

		 trapCommunity OBJECT-TYPE
			SYNTAX DisplayString
			MAX-ACCESS read-write
			STATUS current
			DESCRIPTION
				"SNMP trap community between 1 to 18 characters.
				A community supports all characters except space."
			::= { trap 2 } 
		

		 trapLevel OBJECT-TYPE
			SYNTAX INTEGER
				{
				 ok(1),
				 minor(2),
				 major(3),
				 critical(4) 
				}
			MAX-ACCESS read-write
			STATUS current
			DESCRIPTION
				"The level of trap send.
				Default level is minor.
				ok:send all level message.
				minor:send minor and above level message.
				major:send major and above level message.
				critical:send critical level message."
			::= { trap 3 }                        

		trapMode OBJECT-TYPE
			SYNTAX INTEGER
			{
			eventCodeMode(1),
			trapOidMode(2),
			trapPreciseAlarmMode(3)
			}
			
			MAX-ACCESS read-write
			STATUS current
			DESCRIPTION
				"Trap mode."
			::= { trap 4 }  
			
		trapVersion OBJECT-TYPE
			SYNTAX INTEGER
			{
			v1(1),
			v2c(2),
			v3(3)
			}
			
			MAX-ACCESS read-write
			STATUS current
			DESCRIPTION
				"Trap version."
			::= { trap 5 } 
			
		trapRearm OBJECT-TYPE
			SYNTAX INTEGER
			{
			rearm(1)
			}
			
			MAX-ACCESS read-write
			STATUS current
			DESCRIPTION
				"Send rearm commomnd."
			::= { trap 6 } 
			
		trapServerIdentity OBJECT-TYPE
			SYNTAX INTEGER
			{
			 boardSN(1),
			 productAssetTag(2),
			 hostName(3)
			}
			
			MAX-ACCESS read-write
			STATUS current
			DESCRIPTION
				"Choose the server Identity when sending trap."
			::= { trap 7 }
			
		trapSecurityUserName OBJECT-TYPE
			SYNTAX DisplayString
			MAX-ACCESS read-write
			STATUS current
			DESCRIPTION
				"The security user name for SNMP TRAP V3, the user should be one of the BMC local user."
			::= { trap 8 }  

		 trapLevelDetail OBJECT-TYPE
			SYNTAX DisplayString
			MAX-ACCESS read-write
			STATUS current
			DESCRIPTION
				"The level of trap send.
				Support set/get any combination of the 4 alarm levels(critical,major,minor,normal), use comma to separate them.
				none/all is also supported,but never use it with the 4 levels together.
				
				e.g. To set critical + major level message, just set:
						critical,major
					To set critical level message, just set:
						critical
					To set all level message, just set:
						all"						
			::= { trap 9 } 
			
		--Trap
		trapInfoDescriptionTable OBJECT-TYPE
			SYNTAX SEQUENCE OF TrapInfoDescriptionEntry
			MAX-ACCESS not-accessible
			STATUS current
			DESCRIPTION
				"A table containing the list of Trap information."
			::= { trap 50 }
        
                trapInfoDescriptionEntry OBJECT-TYPE
			SYNTAX TrapInfoDescriptionEntry  
			MAX-ACCESS not-accessible
			STATUS current
			DESCRIPTION
				"Information about a trap group."
			INDEX { trapReceiverIndex }
			::= { trapInfoDescriptionTable 1 }
		
		TrapInfoDescriptionEntry ::=
			SEQUENCE {
				trapReceiverIndex
					INTEGER,
				trapReceiverEnable
					INTEGER,
				trapReceiverAddress
					DisplayString,
				trapReceiverPort 
					INTEGER,    
				trapSendType
					INTEGER,
				trapTest
					INTEGER,
				trapBobEnable
					INTEGER																 					
				} 
			
		trapReceiverIndex OBJECT-TYPE	
			SYNTAX INTEGER
			MAX-ACCESS not-accessible
			STATUS current
			DESCRIPTION
				""
			::= { trapInfoDescriptionEntry 1 } 
		

		trapReceiverEnable OBJECT-TYPE
			SYNTAX INTEGER      
			{
				disable(1),
				enable(2)	
			}
			MAX-ACCESS read-write
			STATUS current
			DESCRIPTION
				"Trap Receiver state enable 2,
				 disable 1."
			::= { trapInfoDescriptionEntry 2 }
        

		trapReceiverAddress OBJECT-TYPE
			SYNTAX DisplayString
			MAX-ACCESS read-write
			STATUS current
			DESCRIPTION
				"Trap Receiver IPv4 addrsss, IPv6 address or domain name.
				Default value is empty."
			::= { trapInfoDescriptionEntry 3 }  


		trapReceiverPort OBJECT-TYPE
			SYNTAX INTEGER
			MAX-ACCESS read-write
			STATUS current
			DESCRIPTION
				"SNMP trap port, default is 162."
			::= { trapInfoDescriptionEntry 4 } 
	

		trapSendType OBJECT-TYPE
			SYNTAX INTEGER 
			{
				snmpTrap(1)	
			}
			MAX-ACCESS read-write
			STATUS current
			DESCRIPTION
				"Send message type snmptrap."
			::= { trapInfoDescriptionEntry 5 }
		

		trapTest OBJECT-TYPE
			SYNTAX INTEGER 
			MAX-ACCESS read-write
			STATUS current
			DESCRIPTION
				"Test the SNMP trap or syslog whether could send.
				When set, the value is only 1."
			::= { trapInfoDescriptionEntry 6 }   
			
		trapBobEnable OBJECT-TYPE
			SYNTAX INTEGER      
			{
				disable(1),
				enable(2)	
			}
			MAX-ACCESS read-write
			STATUS current
			DESCRIPTION
				"BOB: iBMC over iBMA.
				 Use in-band channel forwarding trap: enabled 2,
				                                      disabled 1."
			::= { trapInfoDescriptionEntry 7 }
			
--    ****** SMTP Location *******************************  			

		smtp  OBJECT IDENTIFIER ::= { hwiBMC 5 }                                

  		smtpEnable OBJECT-TYPE
			SYNTAX INTEGER
			{
				disable (1),
				enable (2)				
			}
			MAX-ACCESS read-write
			STATUS current
			DESCRIPTION
				"The state of SMTP. 
				Default value is disable(1)."
			::= { smtp 1 }
		 

		smtpSendSeverity OBJECT-TYPE
			SYNTAX INTEGER
				{
				 ok(1),
				 minor(2),
				 major(3),
				 critical(4) 
				}
			MAX-ACCESS read-write
			STATUS current
			DESCRIPTION
				"The severity of SMTP send.
				Default Severity is ok(1).
				ok:Send all level message.
				minor:Send minor and above level message.
				major:Send major and above level message.
				critical:Send critical level message."
			::= { smtp 2 }
		

		smtpServerIP OBJECT-TYPE
			SYNTAX DisplayString
			MAX-ACCESS read-write
			STATUS current
			DESCRIPTION
				"The SMTP server IPv4 address, IPv6 address or domain name.
				Default value is empty."
			::= { smtp 3 } 
			

		smtpLoginType OBJECT-TYPE
			SYNTAX INTEGER
			{
				anonymous(1),
				account(2)
			}
			MAX-ACCESS read-write
			STATUS current
			DESCRIPTION
				"SMTP login type anonymous 1, account 2.
				Default value is anonymous(1)."
			::= { smtp 4 } 	
			

		smtpLoginAccount OBJECT-TYPE
			SYNTAX DisplayString
			MAX-ACCESS read-write
			STATUS current
			DESCRIPTION
				"Login account between 1 to 64 characters.
				A login account supports all characters except space,double quotationthe,equal and the following characters:#'&."
			::= { smtp 5 } 
			

		smtpLoginPassword OBJECT-TYPE
			SYNTAX DisplayString
			MAX-ACCESS read-write
			STATUS current
			DESCRIPTION
				"Set user login SMTP password.
				Login password between 1 to 50 characters."
			::= { smtp 6 }
			

		smtpSendFrom OBJECT-TYPE
			SYNTAX DisplayString
			MAX-ACCESS read-write
			STATUS current
			DESCRIPTION
				"Send from between 0 to 255 characters.
				A send from supports all characters except space,double quotation,equal and the following characters:#'&."
			::= { smtp 7 }			
			
		smtpTLSEnable OBJECT-TYPE
			SYNTAX INTEGER
			{
				disable (1),
				enable (2)				
			}
			MAX-ACCESS read-write
			STATUS current
			DESCRIPTION
				"The TLS state for SMTP. 
				Default value is enable(2)."
			::= { smtp 8 }			
			

		smtpSendSeverityDetail OBJECT-TYPE
			SYNTAX DisplayString
			MAX-ACCESS read-write
			STATUS current
			DESCRIPTION
				"The severity of SMTP send.
				Support set/get any combination of the 4 alarm levels(critical,major,minor,normal), use comma to separate them.
				none/all is also supported,but never use it with the 4 levels together.
				
				e.g. To set critical + major level message, just set:
						critical,major
					To set critical level message, just set:
						critical
					To set all level message, just set:
						all"	
			::= { smtp 9 }			
			

 		smtpReceiverDescriptionTable OBJECT-TYPE
			SYNTAX SEQUENCE OF SmtpReceiverDescriptionEntry 
			MAX-ACCESS not-accessible
			STATUS current
			DESCRIPTION
				"A table containing the list of SMTP Receiver information."
			::= { smtp 50 }
        
                smtpReceiverDescriptionEntry OBJECT-TYPE
			SYNTAX SmtpReceiverDescriptionEntry  
			MAX-ACCESS not-accessible
			STATUS current
			DESCRIPTION
				"Information about SMTP Receiver information."
			INDEX { smtpReceiverIndex }
			::= { smtpReceiverDescriptionTable 1 }
		
		SmtpReceiverDescriptionEntry ::=
			SEQUENCE {
				smtpReceiverIndex
					INTEGER,
				smtpReceiverState
					INTEGER,
				smtpReceiverAddress
					DisplayString,
				smtpReceiverDescription 
					DisplayString,    
				smtpReceiverTest
					INTEGER																 					
				} 

		smtpReceiverIndex OBJECT-TYPE	
			SYNTAX INTEGER
			MAX-ACCESS not-accessible
			STATUS current
			DESCRIPTION
				"Smtp receiver index."
			::= { smtpReceiverDescriptionEntry 1 } 


		smtpReceiverState OBJECT-TYPE
			SYNTAX INTEGER      
				{
				disable(1),
				enable(2)	
				}
			MAX-ACCESS read-write
			STATUS current
			DESCRIPTION
				"SMTP receiver enable state. Disable 1, enable 2.
				Default value is disable(1)."
			::= { smtpReceiverDescriptionEntry 2 }
        

		smtpReceiverAddress OBJECT-TYPE
			SYNTAX DisplayString
			MAX-ACCESS read-write
			STATUS current
			DESCRIPTION
				"Email address between 0 to 255 characters.
				A email address supports all characters except space,double quotation,equal and the following characters:#'&."
			::= { smtpReceiverDescriptionEntry 3 }  
		

		smtpReceiverDescription OBJECT-TYPE
			SYNTAX DisplayString
			MAX-ACCESS read-write
			STATUS current
			DESCRIPTION
				"Email description between 0 to 255 characters.
				A email description supports all characters except double quotation,equal and the following characters:#'&."
			::= { smtpReceiverDescriptionEntry 4 } 
		

		smtpReceiverTest OBJECT-TYPE
			SYNTAX INTEGER 
			MAX-ACCESS read-write
			STATUS current
			DESCRIPTION
				"Test whether could send email.
				When set, the value is only 1."
			::= { smtpReceiverDescriptionEntry 5 }

--    ****** Syslog Location *******************************

		syslog  OBJECT IDENTIFIER ::= { hwiBMC 34 }


  		syslogEnable OBJECT-TYPE
			SYNTAX INTEGER
					{
					disable (1),
					enable (2)
					}
			MAX-ACCESS read-write
			STATUS current
			DESCRIPTION
				"The enable state of syslog.
				Default value is disable(1)."
			::= { syslog 1 }

		syslogIdentity OBJECT-TYPE
			SYNTAX INTEGER
			{
			 boardSN(1),
			 productAssetTag(2),
			 hostName(3)
			}

			MAX-ACCESS read-write
			STATUS current
			DESCRIPTION
				"Choose the server Identity when sending syslog."
			::= { syslog 2 }

		 syslogSeverity OBJECT-TYPE
			SYNTAX INTEGER
				{
				 ok(1),
				 minor(2),
				 major(3),
				 critical(4),
				 none(5)
				}
			MAX-ACCESS read-write
			STATUS current
			DESCRIPTION
				"The level of syslog send.
				Default level is ok.
				ok:send all level message.
				minor:send minor and above level message.
				major:send major and above level message.
				critical:send critical level message.
				none:send nothing."
			::= { syslog 3 }
		
		syslogProtocolType OBJECT-TYPE
			SYNTAX INTEGER
				{
				udp(1),
				tcp(2),
				tls(3)
				}
			MAX-ACCESS read-write
			STATUS current
			DESCRIPTION
				"The syslog protocol type.
				Default value is TCP.
				udp:When receiving messages using the UDP protocol.
				tcp:When receiving messages using the TCP protocol.
				tls:When receiving messages using the TCP protocol"
			::= { syslog 4 }
		
		syslogAuthType OBJECT-TYPE
			SYNTAX INTEGER
				{
				one-way(1),
				mutual(2)
				}
			MAX-ACCESS read-write
			STATUS current
			DESCRIPTION
				"The syslog auth type.
				Default value is one way authentication.
				one way authentication:authenticate the server.
				mutual authentication:authenticate the server and client."
			::= { syslog 5 }
			
		syslogImportRootCertificate OBJECT-TYPE
			SYNTAX DisplayString
			MAX-ACCESS read-write
			STATUS current
			DESCRIPTION
				"Import root certificate of the syslog server,write only. eg:/tmp/cacert.pem"
			::= { syslog 6 }
		
		syslogImportClientCertificate OBJECT-TYPE
			SYNTAX DisplayString
			MAX-ACCESS read-write
			STATUS current
			DESCRIPTION
				"Import client certificate of the syslog server,write only. eg:/tmp/client.pfx;password"
			::= { syslog 7 }

		--Syslog
		syslogInfoDescriptionTable OBJECT-TYPE
			SYNTAX SEQUENCE OF SyslogInfoDescriptionEntry
			MAX-ACCESS not-accessible
			STATUS current
			DESCRIPTION
				"A table containing the list of Syslog information."
			::= { syslog 50 }

		syslogInfoDescriptionEntry OBJECT-TYPE
			SYNTAX SyslogInfoDescriptionEntry
			MAX-ACCESS not-accessible
			STATUS current
			DESCRIPTION
				"Information about a syslog group."
			INDEX { syslogReceiverIndex }
			::= { syslogInfoDescriptionTable 1 }

		SyslogInfoDescriptionEntry ::=
			SEQUENCE {
				syslogReceiverIndex
					INTEGER,
				syslogReceiverEnable
					INTEGER,
				syslogReceiverAddress
					DisplayString,
				syslogReceiverPort
					INTEGER,
				syslogSendLogType
					DisplayString,
				syslogReceiverTest
					INTEGER
				}

		syslogReceiverIndex OBJECT-TYPE
			SYNTAX INTEGER
			MAX-ACCESS not-accessible
			STATUS current
			DESCRIPTION
				""
			::= { syslogInfoDescriptionEntry 1 }


		syslogReceiverEnable OBJECT-TYPE
			SYNTAX INTEGER
			{
				disable(1),
				enable(2)
			}
			MAX-ACCESS read-write
			STATUS current
			DESCRIPTION
				"Syslog Receiver state enable 2,
				 disable 1."
			::= { syslogInfoDescriptionEntry 2 }


		syslogReceiverAddress OBJECT-TYPE
			SYNTAX DisplayString
			MAX-ACCESS read-write
			STATUS current
			DESCRIPTION
				"Syslog Receiver IP addrsss.
				Default value is empty."
			::= { syslogInfoDescriptionEntry 3 }


		syslogReceiverPort OBJECT-TYPE
			SYNTAX INTEGER
			MAX-ACCESS read-write
			STATUS current
			DESCRIPTION
				"Syslog port."
			::= { syslogInfoDescriptionEntry 4 }

		syslogSendLogType OBJECT-TYPE
			SYNTAX DisplayString
			MAX-ACCESS read-write
			STATUS current
			DESCRIPTION
				"The log type of syslog send.
				Support set/get any combination of the 3 log type(OperationLogs,SecurityLogs,EventLogs), use comma to separate them.
				none/all is also supported,but never use it with the 3 log types together.

				e.g. To set OperationLogs + SecurityLogs log type message, just set:
						OperationLogs,SecurityLogs
					To set EventLogs message, just set:
						EventLogs
					To set none level message, just set:
						none
					To set all level message, just set:
						all"
			::= { syslogInfoDescriptionEntry 5 }

		syslogReceiverTest OBJECT-TYPE
			SYNTAX INTEGER
			MAX-ACCESS read-write
			STATUS current
			DESCRIPTION
				"Test the syslog.
				When set, the value is only 1."
			::= { syslogInfoDescriptionEntry 6 }
		
		--syslog cert 
		syslogCertInfoDescriptionTable OBJECT-TYPE
			SYNTAX SEQUENCE OF SyslogCertInfoDescriptionEntry
			MAX-ACCESS not-accessible
			STATUS current
			DESCRIPTION
				"A table containing the list of Syslog cert information.
				1:root CA.
				2:client cert."
			::= { syslog 51 }
		syslogCertInfoDescriptionEntry OBJECT-TYPE
			SYNTAX SyslogCertInfoDescriptionEntry
			MAX-ACCESS not-accessible
			STATUS current
			DESCRIPTION
				"Information about a syslog cert group."
			INDEX { syslogCertType }
			::= { syslogCertInfoDescriptionTable 1 }

		SyslogCertInfoDescriptionEntry ::=
			SEQUENCE {
				syslogCertType
					INTEGER,
				syslogCertIssuedTo
					DisplayString,
				syslogCertIssuedBy
					DisplayString,
				syslogCertValidFrom
					DisplayString,
				syslogCertValidTo
					DisplayString,
				syslogCertSerialNumber
					DisplayString
				}
				
		syslogCertType OBJECT-TYPE
			SYNTAX INTEGER
			MAX-ACCESS not-accessible
			STATUS current
			DESCRIPTION
				"1: The root CA of syslog server. 
				 2: The client certificate of iBMC."
			::= { syslogCertInfoDescriptionEntry 1 }
		syslogCertIssuedTo OBJECT-TYPE
			SYNTAX DisplayString
			MAX-ACCESS read-only
			STATUS current
			DESCRIPTION
				"Provides information about the user (current server) of an SSL certificate."
			::= { syslogCertInfoDescriptionEntry 2 }
		syslogCertIssuedBy OBJECT-TYPE
			SYNTAX DisplayString
			MAX-ACCESS read-only
			STATUS current
			DESCRIPTION
				"Provides information about the issuer of an SSL certificate. The fields 
				contained in Issued By are the same as those in Issued To."
			::= { syslogCertInfoDescriptionEntry 3 }
		syslogCertValidFrom OBJECT-TYPE
			SYNTAX DisplayString
			MAX-ACCESS read-only
			STATUS current
			DESCRIPTION
				"Indicates the date when an SSL certificate starts to take effect."
			::= { syslogCertInfoDescriptionEntry 4 }
		syslogCertValidTo OBJECT-TYPE
			SYNTAX DisplayString
			MAX-ACCESS read-only
			STATUS current
			DESCRIPTION
				"Indicates the date when an SSL certificate will expire."
			::= { syslogCertInfoDescriptionEntry 5 }
		syslogCertSerialNumber OBJECT-TYPE
			SYNTAX DisplayString
			MAX-ACCESS read-only
			STATUS current
			DESCRIPTION
				"Indicates the serial number of an SSL certificate, used for identifying and 
				migrating the certificate."
			::= { syslogCertInfoDescriptionEntry 6 }
--    ****** PowerSupply Location *******************************
  
		powerSupplyInfo OBJECT IDENTIFIER ::= { hwiBMC 6 }
		

		powerSupplyEntireStatus OBJECT-TYPE
			SYNTAX INTEGER 
				{
				ok(1),
				minor(2),
				major(3),
				critical(4),
				absence(5),
				unknown(6)
				}
			MAX-ACCESS read-only
			STATUS current
			DESCRIPTION
				"Information about all power supply health status."
			::= { powerSupplyInfo 1 }
			
		settedPowerSupplyEntireMode OBJECT-TYPE
			SYNTAX INTEGER 
				{
				loadBalance(1),
				activeStandby(2),
				unsupport(3) 
				}
			MAX-ACCESS read-write
			STATUS current
			DESCRIPTION
				"Setted power supply entire mode.
				 Power supply entire mode get:
					1:loadBalance(1)
					2:activeBackup(2)
					3:unsupport(3) 
				 Power supply entire mode set:
					1:loadBalance(1)
					2:activeBackup(2)
				"
			::= { powerSupplyInfo 2 }
                       
		actualPowerSupplyEntireMode OBJECT-TYPE
			SYNTAX INTEGER 
				{
				loadBalance(1),
				activeStandby(2),
				unknown(3)
				}
			MAX-ACCESS read-only
			STATUS current
			DESCRIPTION
				"Actual power supply entire mode."
			::= { powerSupplyInfo 3 }
			
		settedActivePowerSupply OBJECT-TYPE
			SYNTAX INTEGER 
			MAX-ACCESS read-write
			STATUS current
			DESCRIPTION
				"Setted active power supply. per bit represents a PS, bit0 is PS1, and so on, the bit value of 1 indicates the PS is active.can not set all PS are active or backup.The result 0x7FFFFFFF is unsupport."
			::= { powerSupplyInfo 4 }	
			
		powerSupplyDescriptionTable OBJECT-TYPE
			SYNTAX SEQUENCE OF PowerSupplyDescriptionEntry 
			MAX-ACCESS not-accessible
			STATUS current
			DESCRIPTION
				"A table containing the list of power supply information."
			::= { powerSupplyInfo 50 }
        
                powerSupplyDescriptionEntry OBJECT-TYPE
			SYNTAX PowerSupplyDescriptionEntry
			MAX-ACCESS not-accessible
			STATUS current
			DESCRIPTION
				"Information about power supply."
			INDEX { powerSupplyIndex }
			::= { powerSupplyDescriptionTable 1 }
		
		PowerSupplyDescriptionEntry ::=
			SEQUENCE {
				powerSupplyIndex
					INTEGER, 
				powerSupplymanufacture 
					DisplayString,
				powerSupplyInputMode
					INTEGER,
				powerSupplyModel 
					DisplayString,
				powerSupplyVersion 
					DisplayString, 
				powerSupplyPowerRating 
					INTEGER, 
				powerSupplyStatus 
					INTEGER, 					
				powerSupplyInputPower 
					INTEGER,
				powerSupplyPresence 
					INTEGER,
				powerSupplyProtocol
				    INTEGER	,
				powerSupplyLocation 
					DisplayString,
				powerSupplyFunction
					DisplayString,
				powerSupplyDevicename
				    DisplayString,
				powerSupplyWorkMode
					INTEGER,
				powerSupplySN
					DisplayString
				} 

		powerSupplyIndex OBJECT-TYPE	
			SYNTAX INTEGER
			MAX-ACCESS not-accessible
			STATUS current
			DESCRIPTION
				"Power supply index."
			::= { powerSupplyDescriptionEntry 1 } 
			

		powerSupplymanufacture OBJECT-TYPE
			SYNTAX DisplayString
			MAX-ACCESS read-only
			STATUS current
			DESCRIPTION
				"Information about power manufacture."
			::= { powerSupplyDescriptionEntry 2 }
			

		powerSupplyInputMode OBJECT-TYPE
			SYNTAX INTEGER
			{
			acInput(1),
			dcInput(2),
			acInputDcInput(3)
			}
			MAX-ACCESS read-only
			STATUS current
			DESCRIPTION
				"Information about power input."
			::= { powerSupplyDescriptionEntry 3 }
			

		powerSupplyModel OBJECT-TYPE
			SYNTAX DisplayString
			MAX-ACCESS read-only
			STATUS current
			DESCRIPTION
				"Information about power Model."
			::= { powerSupplyDescriptionEntry 4 } 
			
			

		powerSupplyVersion OBJECT-TYPE
			SYNTAX DisplayString
			MAX-ACCESS read-only
			STATUS current
			DESCRIPTION
				"Information about power version."
			::= { powerSupplyDescriptionEntry 5 }  

			

		powerSupplyPowerRating OBJECT-TYPE
			SYNTAX INTEGER
			MAX-ACCESS read-only
			STATUS current
			DESCRIPTION
				"Information about power rating."
			::= { powerSupplyDescriptionEntry 6 } 			



		powerSupplyStatus OBJECT-TYPE
			SYNTAX INTEGER  
				{
				ok(1),
				minor(2),
				major(3),
				critical(4),
				absence(5),
				unknown(6)
				}
			MAX-ACCESS read-only
			STATUS current
			DESCRIPTION
				"Information about power status."
			::= { powerSupplyDescriptionEntry 7 } 			


		powerSupplyInputPower OBJECT-TYPE
			SYNTAX INTEGER
			MAX-ACCESS read-only
			STATUS current
			DESCRIPTION
				"Information about input power.
				The unit is watt."
			::= { powerSupplyDescriptionEntry 8 } 			    
			

		powerSupplyPresence OBJECT-TYPE
			SYNTAX INTEGER 
				{
				absence(1),
				presence(2),
				unknown(3)
				}
			MAX-ACCESS read-only
			STATUS current
			DESCRIPTION
				"Information about power presence status."
			::= { powerSupplyDescriptionEntry 9 } 
			

		powerSupplyProtocol OBJECT-TYPE
			SYNTAX INTEGER 
				{
				psmi(1),
				pmbus(2)
				}
			MAX-ACCESS read-only
			STATUS current
			DESCRIPTION
				"Information about power protocol."
			::= { powerSupplyDescriptionEntry 10 }
			
		powerSupplyLocation OBJECT-TYPE
			SYNTAX DisplayString
			MAX-ACCESS read-only
			STATUS current
			DESCRIPTION
				"Power supply physical location."
			::= { powerSupplyDescriptionEntry 11 }
		powerSupplyFunction OBJECT-TYPE
			SYNTAX DisplayString
			MAX-ACCESS read-only
			STATUS current
			DESCRIPTION
				"Power supply logic function."
			::= { powerSupplyDescriptionEntry 12 }
		powerSupplyDevicename OBJECT-TYPE
			SYNTAX DisplayString
			MAX-ACCESS read-only
			STATUS current
			DESCRIPTION
				"Power supply devicename."
			::= { powerSupplyDescriptionEntry 13 }	
			
		powerSupplyWorkMode OBJECT-TYPE
			SYNTAX INTEGER 
				{
				active(1),
				backup(2),
				unknown(3)
				}
			MAX-ACCESS read-only
			STATUS current
			DESCRIPTION
				"power supply actual work mode."
			::= { powerSupplyDescriptionEntry 14 }	
		
		powerSupplySN OBJECT-TYPE
			SYNTAX DisplayString
			MAX-ACCESS read-only
			STATUS current
			DESCRIPTION
				"Power supply SN."
			::= { powerSupplyDescriptionEntry 15 }
--    ****** FRU Power Control Property *******************************
  
		fruPowerProperty OBJECT IDENTIFIER ::= { hwiBMC 7 }    

		fruPowerDescriptionTable OBJECT-TYPE
			SYNTAX SEQUENCE OF FruPowerDescriptionEntry 
			MAX-ACCESS not-accessible
			STATUS current
			DESCRIPTION
				"A table containing the list of fru power information."
			::= { fruPowerProperty 50 }
        
                fruPowerDescriptionEntry OBJECT-TYPE
			SYNTAX FruPowerDescriptionEntry
			MAX-ACCESS not-accessible
			STATUS current
			DESCRIPTION
				"Information about fru power supply."
			INDEX { fruNum }
			::= { fruPowerDescriptionTable 1 }
		
		FruPowerDescriptionEntry ::=
			SEQUENCE {
				fruNum
					INTEGER,
				fruPowerControl
					INTEGER
				}
				 

		fruNum OBJECT-TYPE	
			SYNTAX INTEGER
			MAX-ACCESS not-accessible
			STATUS current
			DESCRIPTION
				"The index of the FRU power."
			::= { fruPowerDescriptionEntry 1 }
					
			

		fruPowerControl OBJECT-TYPE
			SYNTAX INTEGER
				{
				normalPowerOff(1),
				powerOn(2),
				forcedSystemReset(3),
				forcedPowerCycle(4)
				}
			MAX-ACCESS read-write
			STATUS current
			DESCRIPTION
				"Information about fru power control."
			::= { fruPowerDescriptionEntry 2 }
			                                                     
--    ****** FAN Information *******************************
  
		fanProperty OBJECT IDENTIFIER ::= { hwiBMC 8 }     
		 

		fanMode OBJECT-TYPE
			SYNTAX DisplayString
			MAX-ACCESS read-write
			STATUS current
			DESCRIPTION
				"Fan control mode manual or auto. 
				 fan mode:   
				 0  - auto	
				 1  - manual	           
				 
				 set format: <mode>,[timeout]
				 get format: <mode>,[timeout]   
				 
				 When <mode> = 0, the format is only <mode>.
				    
				 [timeout] is option and value is in [0,300],unit is second,
				 When set, if fan mode is manual and without [timeout],
				 The default out time is 30 seconds."
			::= { fanProperty 1 } 
			     

		fanLevel OBJECT-TYPE
			SYNTAX INTEGER
			MAX-ACCESS read-write
			STATUS current
			DESCRIPTION
				"Percent of fan speed.
				This value is in [MIN_FANLEVEL,100].
				MIN_FANLEVEL is the minimum fanlevel according to systems,
				particular, when get, 255 represent fan mode is auto."
			::= { fanProperty 2 }
			

		fanEntireStatus OBJECT-TYPE
			SYNTAX INTEGER 
				{
				ok(1),
				minor(2),
				major(3),
				critical(4),
				absence(5),
				unknown(6)
				}
			MAX-ACCESS read-only
			STATUS current
			DESCRIPTION
				"Information about all fan health status."
			::= { fanProperty 3 }
        
		fanDescriptionTable OBJECT-TYPE
			SYNTAX SEQUENCE OF FanDescriptionEntry 
			MAX-ACCESS not-accessible
			STATUS current
			DESCRIPTION
				"A table containing the list of fan information."
			::= { fanProperty 50 }
        
                fanDescriptionEntry OBJECT-TYPE
			SYNTAX FanDescriptionEntry
			MAX-ACCESS not-accessible
			STATUS current
			DESCRIPTION
				"Information about fan information."
			INDEX { fanIndex }
			::= { fanDescriptionTable 1 }
		
		FanDescriptionEntry ::=
			SEQUENCE {
				fanIndex
					INTEGER, 
				fanSpeed
					INTEGER,
				fanPresence
					INTEGER,
				fanStatus
					INTEGER,
				fanLocation
					DisplayString,
				fanFunction
					DisplayString,
				fanDevicename
					DisplayString,	
				fanSpeedRatio
					INTEGER
				}
				 

		fanIndex OBJECT-TYPE	
			SYNTAX INTEGER
			MAX-ACCESS not-accessible
			STATUS current
			DESCRIPTION
				"Fan index."
			::= { fanDescriptionEntry 1 } 
			
			

		fanSpeed OBJECT-TYPE
			SYNTAX INTEGER
			MAX-ACCESS read-only
			STATUS current
			DESCRIPTION
				"Information about fan speed, Unit is RPM."
			::= { fanDescriptionEntry 2 } 
			

		fanPresence OBJECT-TYPE
			SYNTAX INTEGER
				{
				absence(1),
				presence(2),
				unknown(3)
				}
			MAX-ACCESS read-only
			STATUS current
			DESCRIPTION
				"Information about fan presence."
			::= { fanDescriptionEntry 3 }



		fanStatus OBJECT-TYPE
			SYNTAX INTEGER 
				{
				ok(1),
				minor(2),
				major(3),
				critical(4),
				absence(5),
				unknown(6)
				}
			MAX-ACCESS read-only
			STATUS current
			DESCRIPTION
				"Information about fan health status."
			::= { fanDescriptionEntry 4 }
			
		
		fanLocation OBJECT-TYPE
			SYNTAX DisplayString
			MAX-ACCESS read-only
			STATUS current
			DESCRIPTION
				"Fan physical location."
			::= { fanDescriptionEntry 5 } 

		
		fanFunction OBJECT-TYPE
			SYNTAX DisplayString
			MAX-ACCESS read-only
			STATUS current
			DESCRIPTION
				"Fan logic function."
			::= { fanDescriptionEntry 6 } 

		
		fanDevicename OBJECT-TYPE
			SYNTAX DisplayString
			MAX-ACCESS read-only
			STATUS current
			DESCRIPTION
				"Fan devicename."
			::= { fanDescriptionEntry 7 } 	
			
			
			
		fanSpeedRatio OBJECT-TYPE
			SYNTAX INTEGER
			MAX-ACCESS read-only
			STATUS current
			DESCRIPTION
				"Fan speed ratio."
			::= { fanDescriptionEntry 8 } 
			
--    ****** FRU LED Information *******************************
  
		fruLedProperty OBJECT IDENTIFIER ::= { hwiBMC 9 }    

		fruLedDescriptionTable OBJECT-TYPE
			SYNTAX SEQUENCE OF FruLedDescriptionEntry 
			MAX-ACCESS not-accessible
			STATUS current
			DESCRIPTION
				"A table containing the list of led information."
			::= { fruLedProperty 50 }
        
                fruLedDescriptionEntry OBJECT-TYPE
			SYNTAX FruLedDescriptionEntry
			MAX-ACCESS not-accessible
			STATUS current
			DESCRIPTION
				"Information about led."
			INDEX { fruID, ledName }
			::= { fruLedDescriptionTable 1 }
		
		FruLedDescriptionEntry ::=
			SEQUENCE {
			    fruID
			        INTEGER,
				ledName
					DisplayString, 
				ledColorCapbilities
					DisplayString,
				ledColorInLocalControlState
					DisplayString,
				ledColorInOverrideState
					DisplayString,
				ledColor
					DisplayString,
				ledMode
					INTEGER,
				ledStatus
					INTEGER,
				ledLitOnLastTime
					INTEGER,
				ledLitOffLastTime
					INTEGER
				}
				 

		fruID OBJECT-TYPE	
			SYNTAX INTEGER
			MAX-ACCESS not-accessible
			STATUS current
			DESCRIPTION
				"FRU Led index."
			::= { fruLedDescriptionEntry 1 }
		

		ledName OBJECT-TYPE	
			SYNTAX DisplayString
			MAX-ACCESS read-only
			STATUS current
			DESCRIPTION
				"FRU Led name."
			::= { fruLedDescriptionEntry 2 } 
			

		ledColorCapbilities OBJECT-TYPE
			SYNTAX DisplayString
			MAX-ACCESS read-only
			STATUS current
			DESCRIPTION
				"Led capbility: BLUE,RED,GREEN,AMBER,ORANGE,WHITE.
				Return value seprate by ','."
			::= { fruLedDescriptionEntry 3 }
			

		ledColorInLocalControlState OBJECT-TYPE
			SYNTAX DisplayString
			MAX-ACCESS read-only
			STATUS current
			DESCRIPTION
				"Led control state: BLUE,RED,GREEN,AMBER,ORANGE,WHITE."
			::= { fruLedDescriptionEntry 4 }
			

		ledColorInOverrideState OBJECT-TYPE
			SYNTAX DisplayString
			MAX-ACCESS read-only
			STATUS current
			DESCRIPTION
				"Led override: BLUE,RED,GREEN,AMBER,ORANGE,WHITE."
			::= { fruLedDescriptionEntry 5 }


		ledColor OBJECT-TYPE
			SYNTAX DisplayString 
			MAX-ACCESS read-only
			STATUS current
			DESCRIPTION
				"Led color now: BLUE,RED,GREEN,AMBER,ORANGE,WHITE."
			::= { fruLedDescriptionEntry 6 }


		ledMode OBJECT-TYPE
			SYNTAX INTEGER 
				{
				localControl(1),
				override(2),
				test(3)
				}
			MAX-ACCESS read-only
			STATUS current
			DESCRIPTION
				"Information about LED mode."
			::= { fruLedDescriptionEntry 7 } 
			

		ledStatus OBJECT-TYPE
			SYNTAX INTEGER 
				{
				off(1),
				on(2),
				blinking(3)
				}
			MAX-ACCESS read-only
			STATUS current
			DESCRIPTION
				"Information LED status now."
			::= { fruLedDescriptionEntry 8 } 


		ledLitOnLastTime OBJECT-TYPE
			SYNTAX INTEGER 
			MAX-ACCESS read-only
			STATUS current
			DESCRIPTION
				"Unit:10ms(Blinking),100ms(Test)
				 Range:(1~250)*10ms(Blinking),
				       (1~127)*100ms(Test)."
			::= { fruLedDescriptionEntry 9 } 


		ledLitOffLastTime OBJECT-TYPE
			SYNTAX INTEGER 
			MAX-ACCESS read-only
			STATUS current
			DESCRIPTION
				"Unit:10ms(Blinking)
				Range:(1~250)*10ms(Blinking)."
			::= { fruLedDescriptionEntry 10 } 
			

--    ****** Component Information *******************************
  
		componentProperty OBJECT IDENTIFIER ::= { hwiBMC 10 }    

		mezzCardMaxNum OBJECT-TYPE
			SYNTAX INTEGER 
			MAX-ACCESS read-only
			STATUS current
			DESCRIPTION
				"Max number of Mezz Cards."
			::= { componentProperty 1 }
			
		componentDescriptionTable OBJECT-TYPE
			SYNTAX SEQUENCE OF ComponentDescriptionEntry 
			MAX-ACCESS not-accessible
			STATUS obsolete
			DESCRIPTION
				"A table containing the part component."
			::= { componentProperty 50 }
        
                componentDescriptionEntry OBJECT-TYPE
			SYNTAX ComponentDescriptionEntry
			MAX-ACCESS not-accessible
			STATUS obsolete
			DESCRIPTION
				"Information about component."
			INDEX { componentName }
			::= { componentDescriptionTable 1 }
		
		ComponentDescriptionEntry ::=
			SEQUENCE {				
				componentName
					DisplayString, 
				componentType
					INTEGER,
				componentPCBVersion
					DisplayString,
				componentBoardID
					DisplayString,
				componentStatus
					INTEGER
				}
	

		componentName OBJECT-TYPE	
			SYNTAX DisplayString
			MAX-ACCESS read-only
			STATUS obsolete
			DESCRIPTION
				"Information about component name."
			::= { componentDescriptionEntry 1 } 
			

		componentType OBJECT-TYPE
			SYNTAX INTEGER
				{
				baseBoard(1),
				mezzCard(2),
				amcController(3),
				mmcController(4),
				hddBackplane(5),
				raidCard(6),
				pcieCard(9),
				cpuBoard(10),
				memoryBoard(12),
				lomCard(13),
				riserCard(16),
				smmBoard(18),
				chassisBackplane(23),
				fanBackplane(25),
				psuBackplane(26),
				ioBoard(36),
				pcieTransferCard(39),
				m2TransferCard(46),
				gpuBoard(65),
				passThroughCard(68),
				logicalDrive(69),
				pcieRetimer(70),
				horizontalConnectionBoard(76)
				}
			MAX-ACCESS read-only
			STATUS obsolete
			DESCRIPTION
				"Information about component type."
			::= { componentDescriptionEntry 2 }
			

		componentPCBVersion OBJECT-TYPE
			SYNTAX DisplayString
			MAX-ACCESS read-only
			STATUS obsolete
			DESCRIPTION
				"Information about PCB version."
			::= { componentDescriptionEntry 3 }

			

		componentBoardID OBJECT-TYPE
			SYNTAX DisplayString
			MAX-ACCESS read-only
			STATUS obsolete
			DESCRIPTION
				"Information about board ID."
			::= { componentDescriptionEntry 4 } 


		componentStatus OBJECT-TYPE
			SYNTAX INTEGER 
				{
				ok(1),
				minor(2),
				major(3),
				critical(4),
				absence(5),
				unknown(6)
				}
			MAX-ACCESS read-only
			STATUS obsolete
			DESCRIPTION
				"Information about board health status."
			::= { componentDescriptionEntry 5 }		
		
			
--    ****** Firmware Information *******************************
  
		firmwareProperty OBJECT IDENTIFIER ::= { hwiBMC 11 }    

		firmwareDescriptionTable OBJECT-TYPE
			SYNTAX SEQUENCE OF FirmwareDescriptionEntry 
			MAX-ACCESS not-accessible
			STATUS current
			DESCRIPTION
				"A table containing the part firmware."
			::= { firmwareProperty 50 }
        
                firmwareDescriptionEntry OBJECT-TYPE
			SYNTAX FirmwareDescriptionEntry
			MAX-ACCESS not-accessible
			STATUS current
			DESCRIPTION
				"Information about firmware."
			INDEX { firmwareName }
			::= { firmwareDescriptionTable 1 }
		
		FirmwareDescriptionEntry ::=
			SEQUENCE {
				fruNumber
					INTEGER,
				firmwareName
					DisplayString, 
				firmwareType
					INTEGER,
				firmwareReleaseDate
					DisplayString,
				firmwareVersion
					DisplayString,
				firmwareLocation
					DisplayString,
				firmwareBoard
					DisplayString
				} 
				

		firmwareName OBJECT-TYPE	
			SYNTAX DisplayString
			MAX-ACCESS read-only
			STATUS current
			DESCRIPTION
				"Information about firmware name."
			::= { firmwareDescriptionEntry 1 } 
			

		firmwareType OBJECT-TYPE
			SYNTAX INTEGER
				{
				iBMC(1),
				fpga(2),
				cpld(3),
				bios(4),
				uboot(5),
				lcd(6),
				backupUboot(7),
				ioboardCpld(8),
				cpuboardCpld(9),
				hddBackplaneCpld(10),
				pcieRiserCardCpld(11),
				raidCardCpld(12),
				peripheralFirmware(13),
				gpuBoardCpld(14)
				}
			MAX-ACCESS read-only
			STATUS current
			DESCRIPTION
				"Information about firmware type."
			::= { firmwareDescriptionEntry 2 }
			

		firmwareReleaseDate OBJECT-TYPE
			SYNTAX DisplayString
			MAX-ACCESS read-only
			STATUS current
			DESCRIPTION
				"Information about firmware release date."
			::= { firmwareDescriptionEntry 3 }

			

		firmwareVersion OBJECT-TYPE
			SYNTAX DisplayString
			MAX-ACCESS read-only
			STATUS current
			DESCRIPTION
				"Information about firmware version."
			::= { firmwareDescriptionEntry 4 }     
			

		firmwareLocation OBJECT-TYPE
			SYNTAX DisplayString
			MAX-ACCESS read-only
			STATUS current
			DESCRIPTION
				"Information about firmware location."
			::= { firmwareDescriptionEntry 5 }  
			                                                     
		fruNumber OBJECT-TYPE	
			SYNTAX INTEGER
			MAX-ACCESS not-accessible
			STATUS current
			DESCRIPTION
				"Information about FRU id."
			::= { firmwareDescriptionEntry 6 }
			

		firmwareBoard OBJECT-TYPE
			SYNTAX DisplayString
			MAX-ACCESS read-only
			STATUS current
			DESCRIPTION
				"Information about firmware Board."
			::= { firmwareDescriptionEntry 7 }
--    ****** Network Information *******************************
  
		networkProperty OBJECT IDENTIFIER ::= { hwiBMC 12 }    

		networkDescriptionTable OBJECT-TYPE
			SYNTAX SEQUENCE OF NetworkDescriptionEntry 
			MAX-ACCESS not-accessible
			STATUS current
			DESCRIPTION
				"A table containing the ethernet."
			::= { networkProperty 50 }
        
                networkDescriptionEntry OBJECT-TYPE
			SYNTAX NetworkDescriptionEntry
			MAX-ACCESS not-accessible
			STATUS current
			DESCRIPTION
				"Information about ethernet."
			INDEX { ethNum }
			::= { networkDescriptionTable 1 }
		
		NetworkDescriptionEntry ::=
			SEQUENCE {
				ethNum
					INTEGER, 
				ethIPAddress
					IpAddress,
				ethNetmask
					IpAddress,
				ethDefaultGateway
					IpAddress,
				ethIPSource
					INTEGER,
				ethMACAddress
					DisplayString,
				ethType
					INTEGER,
				ethHostPort
					INTEGER,
				ethEnable
					INTEGER,
				ethMode
					INTEGER,
				vlanID
					DisplayString,
				ethInfo
					DisplayString,
				ethIPv4Enable
					INTEGER
				}
				 

		ethNum OBJECT-TYPE	
			SYNTAX INTEGER
			MAX-ACCESS not-accessible
			STATUS current
			DESCRIPTION
				"Information about ethernet port number."
			::= { networkDescriptionEntry 1 } 
			

		ethIPAddress OBJECT-TYPE
			SYNTAX IpAddress
			MAX-ACCESS read-write
			STATUS current
			DESCRIPTION
				"Information about ethernet IP address."
			::= { networkDescriptionEntry 2 }
			

		ethNetmask OBJECT-TYPE
			SYNTAX IpAddress
			MAX-ACCESS read-write
			STATUS current
			DESCRIPTION
				"Information about netmask."
			::= { networkDescriptionEntry 3 }

			

		ethDefaultGateway OBJECT-TYPE
			SYNTAX IpAddress
			MAX-ACCESS read-write
			STATUS current
			DESCRIPTION
				"Information about default gateway."
			::= { networkDescriptionEntry 4 }  



		ethIPSource OBJECT-TYPE
			SYNTAX INTEGER 
				{
				static(1),
				dhcp(2)
				}
			MAX-ACCESS read-write
			STATUS current
			DESCRIPTION
				"Information about IP source."
			::= { networkDescriptionEntry 5 }  	
			

		ethMACAddress OBJECT-TYPE
			SYNTAX DisplayString 
			MAX-ACCESS read-only
			STATUS current
			DESCRIPTION
				"Information about MAC address."
			::= { networkDescriptionEntry 6 }
			

		ethType OBJECT-TYPE
			SYNTAX INTEGER 
				{
				mgmt(1),
				share(2)
				}
			MAX-ACCESS read-only
			STATUS current
			DESCRIPTION
				"Information about ethernet port type."
			::= { networkDescriptionEntry 7 }
			

		ethHostPort OBJECT-TYPE
			SYNTAX INTEGER 
				{
				none(1),
				port1(2),
				port2(3),
				port3(4),
				port4(5)
				}
			MAX-ACCESS read-write
			STATUS current
			DESCRIPTION
				"Information about share ethernet binded host port."
			::= { networkDescriptionEntry 8 }       
			

		ethEnable OBJECT-TYPE
			SYNTAX INTEGER
			{
				disable(1),
				enable(2)
			}
			MAX-ACCESS read-write
			STATUS obsolete
			DESCRIPTION
				"Information about eth enabled."
			::= { networkDescriptionEntry 9 } 			
			

		ethMode OBJECT-TYPE
			SYNTAX INTEGER 
				{
				dedicated (1),
				lomShare(2),
				adaptive(3),
				pcieShare(4)
				}
			MAX-ACCESS read-write
			STATUS current
			DESCRIPTION
				"Information about ethernet Mode."
			::= { networkDescriptionEntry 10 }		
	

		vlanID OBJECT-TYPE
			SYNTAX DisplayString 
			MAX-ACCESS read-write
			STATUS current
			DESCRIPTION
				"Disable or enable VLAN and set ID.
				 Set 'off' to disabled VLAN.
				 Set [1,4094] to enable VLAN and set ID."
			::= { networkDescriptionEntry 11 }
		
        
		ethInfo OBJECT-TYPE
			SYNTAX DisplayString 
			MAX-ACCESS read-write
			STATUS current
			DESCRIPTION
				"Set IPaddr,Netmask,Gateway.
				eg.: 192.168.2.100,255.255.255.0,192.168.2.1"
			::= { networkDescriptionEntry 12 }

		ethIPv4Enable OBJECT-TYPE
			SYNTAX INTEGER
			{
				disable(1),
				enable(2)
			}
			MAX-ACCESS read-write
			STATUS current
			DESCRIPTION
				"Information about eth IPv4 enabled."
			::= { networkDescriptionEntry 13 }
			
--    ****** Sensor Information *******************************
  
		sensorProperty OBJECT IDENTIFIER ::= { hwiBMC 13 }    

		sensorDescriptionTable OBJECT-TYPE
			SYNTAX SEQUENCE OF SensorDescriptionEntry 
			MAX-ACCESS not-accessible
			STATUS current
			DESCRIPTION
				"A table containing the sensor."
			::= { sensorProperty 50 }
        
                sensorDescriptionEntry OBJECT-TYPE
			SYNTAX SensorDescriptionEntry
			MAX-ACCESS not-accessible
			STATUS current
			DESCRIPTION
				"Information about sensor."
			INDEX { sensorName }
			::= { sensorDescriptionTable 1 }
		
		SensorDescriptionEntry ::=
			SEQUENCE {
				sensorName
					DisplayString, 
				sensorReading
					DisplayString,
				sensorUpperNonRecoverable
					DisplayString,
				sensorUpperCritical
					DisplayString,
				sensorUpperMinor
					DisplayString,
				sensorLowerNonRecoverable
					DisplayString,
				sensorLowerCritical
					DisplayString,
				sensorLowerMinor
					DisplayString, 
				sensorStatus
					DisplayString,
				sensorType
					INTEGER,
				sensorPositiveHysteresis
					INTEGER,
				sensorNegativeHysteresis					
				    INTEGER,
				sensorPositiveHysteresisString
					DisplayString,
				sensorNegativeHysteresisString					
				    DisplayString,
				sensorUnit
					INTEGER,
				sensorEventReadingType
				INTEGER
				}


		sensorName OBJECT-TYPE	
			SYNTAX DisplayString
			MAX-ACCESS read-only
			STATUS current
			DESCRIPTION
				"Information about sensor name."
			::= { sensorDescriptionEntry 1 } 
			

		sensorReading OBJECT-TYPE
			SYNTAX DisplayString
			MAX-ACCESS read-only
			STATUS current
			DESCRIPTION
				"Sensor current reading."
			::= { sensorDescriptionEntry 2 }
			

		sensorUpperNonRecoverable OBJECT-TYPE
			SYNTAX DisplayString
			MAX-ACCESS read-only
			STATUS current
			DESCRIPTION
				"Information about sensor upper nonrecoverable threshold."
			::= { sensorDescriptionEntry 3 }

			

		sensorUpperCritical OBJECT-TYPE
			SYNTAX DisplayString
			MAX-ACCESS read-only
			STATUS current
			DESCRIPTION
				"Information about sensor upper crtical threshold."
			::= { sensorDescriptionEntry 4 }  



		sensorUpperMinor OBJECT-TYPE
			SYNTAX DisplayString 
			MAX-ACCESS read-only
			STATUS current
			DESCRIPTION
				"Information about sensor upper minor threshold."
			::= { sensorDescriptionEntry 5 }  	
			

		sensorLowerNonRecoverable OBJECT-TYPE
			SYNTAX DisplayString 
			MAX-ACCESS read-only
			STATUS current
			DESCRIPTION
				"Information about sensor lower nonrecoverable threshold."
			::= { sensorDescriptionEntry 6 } 



		sensorLowerCritical OBJECT-TYPE
			SYNTAX DisplayString 
			MAX-ACCESS read-only
			STATUS current
			DESCRIPTION
				"Information about sensor lower crtical threshold."
			::= { sensorDescriptionEntry 7 } 
			

		sensorLowerMinor OBJECT-TYPE
			SYNTAX DisplayString 
			MAX-ACCESS read-only
			STATUS current
			DESCRIPTION
				"Information about sensor lower minor threshold."
			::= { sensorDescriptionEntry 8 } 
			
			

		sensorStatus OBJECT-TYPE
			SYNTAX DisplayString 
			MAX-ACCESS read-only
			STATUS current
			DESCRIPTION
				"Information about sensor status."
			::= { sensorDescriptionEntry 9 } 
			

		sensorType OBJECT-TYPE
			SYNTAX INTEGER 
			MAX-ACCESS read-only
			STATUS current
			DESCRIPTION
				"Information about sensor type."
			::= { sensorDescriptionEntry 10 } 		
			

		sensorPositiveHysteresis OBJECT-TYPE
			SYNTAX INTEGER 
			MAX-ACCESS read-only
			STATUS current
			DESCRIPTION
				"Positive-going Threshold Hysteresis Value. Set to 00h if sensor does not 
				support positive-going threshold hysteresis. This value is subtracted from 
				positive going thresholds to determine the point where the asserted status for 
				that threshold will clear. See section 35.13.2, Hysteresis and Event Status and 
				section 35.13.3, High-going versus Low-going Threshold Events.  "
			::= { sensorDescriptionEntry 11 }	


		sensorNegativeHysteresis OBJECT-TYPE
			SYNTAX INTEGER 
			MAX-ACCESS read-only
			STATUS current
			DESCRIPTION
				"Negative-going Threshold Hysteresis Value. This value is added  to negative 
				going thresholds to determine the point where the asserted status for that 
				threshold will clear. Set to 00h if sensor does not support negative-going 
				threshold hysteresis. "
			::= { sensorDescriptionEntry 12 }			
			

		sensorPositiveHysteresisString OBJECT-TYPE
			SYNTAX DisplayString 
			MAX-ACCESS read-only
			STATUS current
			DESCRIPTION
				"Positive-going Threshold Hysteresis Value. Set to 'na' if sensor does not 
				support positive-going threshold hysteresis. This value is subtracted from 
				positive going thresholds to determine the point where the asserted status for 
				that threshold will clear. See section 35.13.2, Hysteresis and Event Status and 
				section 35.13.3, High-going versus Low-going Threshold Events.  "
			::= { sensorDescriptionEntry 13 }	


		sensorNegativeHysteresisString  OBJECT-TYPE
			SYNTAX DisplayString 
			MAX-ACCESS read-only
			STATUS current
			DESCRIPTION
				"Negative-going Threshold Hysteresis Value. This value is added  to negative 
				going thresholds to determine the point where the asserted status for that 
				threshold will clear. Set to 'na' if sensor does not support negative-going 
				threshold hysteresis. "
			::= { sensorDescriptionEntry 14 }
        
        sensorUnit OBJECT-TYPE
			SYNTAX INTEGER 
					{
					unspecified (0),
					degrees-c (1),
					degrees-f (2),
					degrees-k (3),
					volts (4),
					amps (5),
					watts (6),
					rpm (18)				
					}
			MAX-ACCESS read-only
			STATUS current
			DESCRIPTION
				"Information about sensor unit."
			::= { sensorDescriptionEntry 15 } 

        sensorEventReadingType OBJECT-TYPE
			SYNTAX INTEGER 
			MAX-ACCESS read-only
			STATUS current
			DESCRIPTION
				"Information about event reading type."
			::= { sensorDescriptionEntry 16 } 			
			
--    ****** Local User Information *******************************
  
		userProperty OBJECT IDENTIFIER ::= { hwiBMC 14 }    

		userDescriptionTable OBJECT-TYPE
			SYNTAX SEQUENCE OF UserDescriptionEntry 
			MAX-ACCESS not-accessible
			STATUS current
			DESCRIPTION
				"A table containing the user."
			::= { userProperty 50 }
        
                userDescriptionEntry OBJECT-TYPE
			SYNTAX UserDescriptionEntry
			MAX-ACCESS not-accessible
			STATUS current
			DESCRIPTION
				"Information about user."
			INDEX { userID }
			::= { userDescriptionTable 1 }
		
		UserDescriptionEntry ::=
			SEQUENCE {
				userID
					INTEGER, 
				userEnable
					INTEGER,
				userName
					DisplayString,
				userPassword
					DisplayString,
				userGroupID
					INTEGER,
				userDelete
				    INTEGER,
				userInterfaces
				    INTEGER,
				userPublicKeyAdd
					DisplayString,
				userPublicKeyDelete
					DisplayString,
				userPublicKeyHash
					DisplayString,
				userSNMPPrivacyPassword
					DisplayString
				}
				 

		userID OBJECT-TYPE	
			SYNTAX INTEGER
			MAX-ACCESS not-accessible
			STATUS current
			DESCRIPTION
				"Information about user id, the vaule is in [2, 17]."
			::= { userDescriptionEntry 1 } 
			

		userEnable OBJECT-TYPE
			SYNTAX INTEGER
				{
				disable(1),
				enable(2)
				}
			MAX-ACCESS read-write
			STATUS current
			DESCRIPTION
				"Information about user enable status , disable 1, enable 2.
				Default value is disable(1)."
			::= { userDescriptionEntry 2 }
			

		userName OBJECT-TYPE
			SYNTAX DisplayString
			MAX-ACCESS read-write
			STATUS current
			DESCRIPTION
				"User name length is 1 to 16 characters.
				The value can contain letters, digits, and special characters. The value cannot contain spaces, double quotation and the following special characters: , \ : < > & ' / %, and cannot start with a number sign (#)."
			::= { userDescriptionEntry 3 }


		userPassword OBJECT-TYPE
			SYNTAX DisplayString
			MAX-ACCESS read-write
			STATUS current
			DESCRIPTION
				"Information about user password. User password length is 1 to 20 characters."
			::= { userDescriptionEntry 4 }  


		userGroupID OBJECT-TYPE
			SYNTAX INTEGER 
			{
				commonUser(1),
				operator(2),
				administrator(3),
				noAccess(4),
				customRole1(5),
				customRole2(6),
				customRole3(7),
				customRole4(8)
			}
			MAX-ACCESS read-write
			STATUS current
			DESCRIPTION
				"Information about user group.
				When set, this vaule will be one of the following:(1, 2, 3, 5, 6, 7, 8).
				1 - common user
				2 - operator 
				3 - administrator  
				4 - no access(only for get)
				5 - custom role1
				6 - custom role2 
				7 - custom role3  
				8 - custom role4."
			::= { userDescriptionEntry 5 }  
			

		userDelete OBJECT-TYPE
			SYNTAX INTEGER 
			{
				delete(1)
			}
			MAX-ACCESS read-write
			STATUS current
			DESCRIPTION
				"Information about delete user.
				This vaule will be one of the following:
				(delete(1))."
			::= { userDescriptionEntry 6 } 	
			
		userInterfaces OBJECT-TYPE
			SYNTAX INTEGER
			MAX-ACCESS read-write
			STATUS current
			DESCRIPTION
				"Information about user login interfaces.
				bit0 - Web:    0 disabled; 1 enabled
				bit1 - SNMP:   0 disabled; 1 enabled
				bit2 - IPMI:   0 disabled; 1 enabled
				bit3 - SSH:    0 disabled; 1 enabled
				bit4 - SFTP:   0 disabled; 1 enabled
				bit6 - Local:  0 disabled; 1 enabled
				bit7 - Redfish:0 disabled; 1 enabled"
			::= { userDescriptionEntry 7 }
			
		userPublicKeyAdd OBJECT-TYPE
			SYNTAX DisplayString
			MAX-ACCESS read-write
			STATUS current
			DESCRIPTION
				"Add PublicKey, the set format is: <publickey file>, with max length 256."
			::= { userDescriptionEntry 8 }  
			
		userPublicKeyDelete OBJECT-TYPE
			SYNTAX DisplayString
			MAX-ACCESS read-write
			STATUS current
			DESCRIPTION
				"Delete PublicKey"
			::= { userDescriptionEntry 9 }  
			
		userPublicKeyHash OBJECT-TYPE
			SYNTAX DisplayString
			MAX-ACCESS read-only
			STATUS current
			DESCRIPTION
				"PublicKey Hash"
			::= { userDescriptionEntry 10 }  
			
		userSNMPPrivacyPassword OBJECT-TYPE
			SYNTAX DisplayString
			MAX-ACCESS read-write
			STATUS current
			DESCRIPTION
				"Information about SNMP privacy password of user. Password length is 1 to 20 characters. 
				 It is not supported on server of V3 series."
			::= { userDescriptionEntry 11 }

--    ****** CPU Information *******************************
  
		cpuProperty OBJECT IDENTIFIER ::= { hwiBMC 15 }    
		

		cpuEntireStatus OBJECT-TYPE
			SYNTAX INTEGER 
				{
				ok(1),
				minor(2),
				major(3),
				critical(4),
				absence(5),
				unknown(6)
				}
			MAX-ACCESS read-only
			STATUS current
			DESCRIPTION
				"Information about all cpu health status."
			::= { cpuProperty 1 }
			
		cpuDescriptionTable OBJECT-TYPE
			SYNTAX SEQUENCE OF CPUDescriptionEntry 
			MAX-ACCESS not-accessible
			STATUS current
			DESCRIPTION
				"A table containing the CPU information."
			::= { cpuProperty 50 }
        
                cpuDescriptionEntry OBJECT-TYPE
			SYNTAX CPUDescriptionEntry
			MAX-ACCESS not-accessible
			STATUS current
			DESCRIPTION
				"Information about CPU."
			INDEX { cpuIndex }
			::= { cpuDescriptionTable 1 }
		
		CPUDescriptionEntry ::=
			SEQUENCE {
				cpuIndex
					INTEGER, 
				cpuManufacturer
					DisplayString,
				cpuFamily
					DisplayString,
				cpuType
					DisplayString,
				cpuClockRate
					DisplayString,
				cpuStatus
					INTEGER,
				cpuAvailability
				        INTEGER,
				cpuLocation
					DisplayString,
				cpuFunction
					DisplayString,
				cpuDevicename
					DisplayString,
				cpuProcessorID
					DisplayString,
				cpuCoreCount
					INTEGER,
				cpuThreadCount
					INTEGER,
				cpuMemoryTechnology
					DisplayString,
				cpuL1Cache-K
					INTEGER,
				cpuL2Cache-K
					INTEGER,
				cpuL3Cache-K
					INTEGER
				}
				 

		cpuIndex OBJECT-TYPE	
			SYNTAX INTEGER
			MAX-ACCESS not-accessible
			STATUS current
			DESCRIPTION
				"Information about CPU index."
			::= { cpuDescriptionEntry 1 } 
			

		cpuManufacturer OBJECT-TYPE
			SYNTAX DisplayString
			MAX-ACCESS read-only
			STATUS current
			DESCRIPTION
				"Information about CPU manufacturer."
			::= { cpuDescriptionEntry 2 }
			

		cpuFamily OBJECT-TYPE
			SYNTAX DisplayString
			MAX-ACCESS read-only
			STATUS current
			DESCRIPTION
				"Information about CPU family."
			::= { cpuDescriptionEntry 3 }

			

		cpuType OBJECT-TYPE
			SYNTAX DisplayString
			MAX-ACCESS read-only
			STATUS current
			DESCRIPTION
				"Information about CPU type."
			::= { cpuDescriptionEntry 4 }  



		cpuClockRate OBJECT-TYPE
			SYNTAX DisplayString 
			MAX-ACCESS read-only
			STATUS current
			DESCRIPTION
				"Information about CPU clock rate."
			::= { cpuDescriptionEntry 5 }  	
			
			

		cpuStatus OBJECT-TYPE
			SYNTAX INTEGER 
				{
				ok(1),
				minor(2),
				major(3),
				critical(4),
				absence(5),
				unknown(6)
				}
			MAX-ACCESS read-only
			STATUS current
			DESCRIPTION
				"Information about CPU health status."
			::= { cpuDescriptionEntry 6 }
		
		

		cpuAvailability OBJECT-TYPE
			SYNTAX INTEGER 
				{
				unknown(1),
				disabled(2),
				backup(3),
				active(4)
				}
			MAX-ACCESS read-only
			STATUS current
			DESCRIPTION
				"Information about CPU availability."
			::= { cpuDescriptionEntry 7 } 
		
		
		cpuLocation OBJECT-TYPE
			SYNTAX DisplayString 
			MAX-ACCESS read-only
			STATUS current
			DESCRIPTION
				"CPU physical location."
			::= { cpuDescriptionEntry 8 }  	

        
		cpuFunction OBJECT-TYPE
			SYNTAX DisplayString 
			MAX-ACCESS read-only
			STATUS current
			DESCRIPTION
				"CPU logic function."
			::= { cpuDescriptionEntry 9 }  	

        
		cpuDevicename OBJECT-TYPE
			SYNTAX DisplayString 
			MAX-ACCESS read-only
			STATUS current
			DESCRIPTION
				"CPU devicename."
			::= { cpuDescriptionEntry 10 }  
							
		cpuProcessorID OBJECT-TYPE
			SYNTAX DisplayString 
			MAX-ACCESS read-only
			STATUS current
			DESCRIPTION
				"CPU ProcessorID."
			::= { cpuDescriptionEntry 11 }
			
		cpuCoreCount OBJECT-TYPE
			SYNTAX INTEGER 
			MAX-ACCESS read-only
			STATUS current
			DESCRIPTION
				"CPU CoreCount."
			::= { cpuDescriptionEntry 12 }  
			
		cpuThreadCount OBJECT-TYPE
			SYNTAX INTEGER 
			MAX-ACCESS read-only
			STATUS current
			DESCRIPTION
				"CPU ThreadCount."
			::= { cpuDescriptionEntry 13 }  
			
		cpuMemoryTechnology OBJECT-TYPE
			SYNTAX DisplayString 
			MAX-ACCESS read-only
			STATUS current
			DESCRIPTION
				"CPU memory technology."
			::= { cpuDescriptionEntry 14 }  
			
		cpuL1Cache-K OBJECT-TYPE
			SYNTAX INTEGER 
			MAX-ACCESS read-only
			STATUS current
			DESCRIPTION
				"CPU Cache."
			::= { cpuDescriptionEntry 15 }
			
		cpuL2Cache-K OBJECT-TYPE
			SYNTAX INTEGER 
			MAX-ACCESS read-only
			STATUS current
			DESCRIPTION
				"CPU Cache."
			::= { cpuDescriptionEntry 16 }
			
		cpuL3Cache-K OBJECT-TYPE
			SYNTAX INTEGER 
			MAX-ACCESS read-only
			STATUS current
			DESCRIPTION
				"CPU Cache."
			::= { cpuDescriptionEntry 17 }
--    ****** Memory Information *******************************
  
		memoryProperty OBJECT IDENTIFIER ::= { hwiBMC 16 }
		

		memoryEntireStatus OBJECT-TYPE
			SYNTAX INTEGER 
				{
				ok(1),
				minor(2),
				major(3),
				critical(4),
				absence(5),
				unknown(6)
				}
			MAX-ACCESS read-only
			STATUS current
			DESCRIPTION
				"Information about all memory health status."
			::= { memoryProperty 1 }     

		memoryDescriptionTable OBJECT-TYPE
			SYNTAX SEQUENCE OF MemoryDescriptionEntry 
			MAX-ACCESS not-accessible
			STATUS current
			DESCRIPTION
				"A table containing the memory."
			::= { memoryProperty 50 }
        
                memoryDescriptionEntry OBJECT-TYPE
			SYNTAX MemoryDescriptionEntry
			MAX-ACCESS not-accessible
			STATUS current
			DESCRIPTION
				"Information about memory."
			INDEX { memoryDimmIndex }
			::= { memoryDescriptionTable 1 }
		
		MemoryDescriptionEntry ::=
			SEQUENCE {
				memoryDimmIndex
					INTEGER, 
				memoryLogic
					DisplayString,
				memoryManufacturer
					DisplayString,
				memorySize
					DisplayString,
				memoryClockRate
					DisplayString,
				memoryStatus
					INTEGER,
				memoryAvailability 
					INTEGER,
				memoryLocation
					DisplayString,
				memoryFunction
					DisplayString,
				memoryDevicename
					DisplayString,
				memoryType
					DisplayString,
				memorySN
					DisplayString,
				memoryMinimumVoltage
					INTEGER,
				memoryRank
					INTEGER,
				memoryBitWidth
					INTEGER,
				memoryTechnology
					DisplayString,
				memoryRemainingServiceLife
					INTEGER,
				memoryFirmwareVersion
					DisplayString,
				memoryMediumTemperature
					DisplayString,
				memoryControllerTemperature
					DisplayString,
				memoryVolatileCapacityMB
					INTEGER,
				memoryPersistentCapacityMB
					INTEGER,				
				}
				 

		memoryDimmIndex OBJECT-TYPE	
			SYNTAX INTEGER
			MAX-ACCESS not-accessible
			STATUS current
			DESCRIPTION
				"Information about memory DIMM index."
			::= { memoryDescriptionEntry 1 } 
			

		memoryLogic OBJECT-TYPE
			SYNTAX DisplayString
			MAX-ACCESS read-only
			STATUS current
			DESCRIPTION
				"Information about memory logic channel."
			::= { memoryDescriptionEntry 2 }
			

		memoryManufacturer OBJECT-TYPE
			SYNTAX DisplayString
			MAX-ACCESS read-only
			STATUS current
			DESCRIPTION
				"Information about memory manufacturer."
			::= { memoryDescriptionEntry 3 }


		memorySize OBJECT-TYPE
			SYNTAX DisplayString
			MAX-ACCESS read-only
			STATUS current
			DESCRIPTION
				"Information about memory capacity."
			::= { memoryDescriptionEntry 4 }  


		memoryClockRate OBJECT-TYPE
			SYNTAX DisplayString 
			MAX-ACCESS read-only
			STATUS current
			DESCRIPTION
				"Information about memory clock rate."
			::= { memoryDescriptionEntry 5 }
			

		memoryStatus OBJECT-TYPE
			SYNTAX INTEGER 
				{
				ok(1),
				minor(2),
				major(3),
				critical(4),
				absence(5),
				unknown(6)
				}
			MAX-ACCESS read-only
			STATUS current
			DESCRIPTION
				"Information about memory health status."
			::= { memoryDescriptionEntry 6 }  	
		

		memoryAvailability OBJECT-TYPE
			SYNTAX INTEGER 
				{
				unknown(1),
				disabled(2),
				backup(3),
				active(4)
				}
			MAX-ACCESS read-only
			STATUS current
			DESCRIPTION
				"Information about memory availability."
			::= { memoryDescriptionEntry 7 } 
			
		memoryLocation OBJECT-TYPE
			SYNTAX DisplayString 
			MAX-ACCESS read-only
			STATUS current
			DESCRIPTION
				"Memory physical location."
			::= { memoryDescriptionEntry 8 }
			
		
		memoryFunction OBJECT-TYPE
			SYNTAX DisplayString 
			MAX-ACCESS read-only
			STATUS current
			DESCRIPTION
				"Memory logic function."
			::= { memoryDescriptionEntry 9 }

		
		memoryDevicename OBJECT-TYPE
			SYNTAX DisplayString 
			MAX-ACCESS read-only
			STATUS current
			DESCRIPTION
				"Memory devicename."
			::= { memoryDescriptionEntry 10 }

		memoryType OBJECT-TYPE
			SYNTAX DisplayString
			MAX-ACCESS read-only
			STATUS current
			DESCRIPTION
				"Information about memory type."
			::= { memoryDescriptionEntry 11 }  
			
		memorySN OBJECT-TYPE
			SYNTAX DisplayString
			MAX-ACCESS read-only
			STATUS current
			DESCRIPTION
				"Information about memory SN."
			::= { memoryDescriptionEntry 12 }  
			
		memoryMinimumVoltage OBJECT-TYPE
			SYNTAX INTEGER
			MAX-ACCESS read-only
			STATUS current
			DESCRIPTION
				"Information about memory minimum voltage."
			::= { memoryDescriptionEntry 13 }  

		memoryRank OBJECT-TYPE
			SYNTAX INTEGER
			MAX-ACCESS read-only
			STATUS current
			DESCRIPTION
				"Information about memory rank."
			::= { memoryDescriptionEntry 14 }  
			
		memoryBitWidth OBJECT-TYPE
			SYNTAX INTEGER
			MAX-ACCESS read-only
			STATUS current
			DESCRIPTION
				"Information about memory bit width."
			::= { memoryDescriptionEntry 15 }  

		memoryTechnology OBJECT-TYPE
			SYNTAX DisplayString
			MAX-ACCESS read-only
			STATUS current
			DESCRIPTION
				"Information about memory technology."
			::= { memoryDescriptionEntry 16 }  

		memoryRemainingServiceLife OBJECT-TYPE
			SYNTAX INTEGER
				{
				unknown(255)
				}
			MAX-ACCESS read-only
			STATUS current
			DESCRIPTION
			    "Remaining endurance in percentage.
				It is available only for DCPMM."
			::= { memoryDescriptionEntry 17 }  

		memoryFirmwareVersion OBJECT-TYPE
			SYNTAX DisplayString
			MAX-ACCESS read-only
			STATUS current
			DESCRIPTION
		        "Memory firmware version information.
				It is available only for DCPMM."
			::= { memoryDescriptionEntry 18 }			
			
		memoryMediumTemperature OBJECT-TYPE
			SYNTAX DisplayString
			MAX-ACCESS read-only
			STATUS current
			DESCRIPTION
		        "Memory medium temperature (in Celsius).
				It is available only for DCPMM."
			::= { memoryDescriptionEntry 19 }  

		memoryControllerTemperature OBJECT-TYPE
			SYNTAX DisplayString
			MAX-ACCESS read-only
			STATUS current
			DESCRIPTION
		        "Memory controller temperature (in Celsius).
				It is available only for DCPMM."
			::= { memoryDescriptionEntry 20 }  

			
		memoryVolatileCapacityMB OBJECT-TYPE
			SYNTAX INTEGER
				{
				unknown(-1)
				}
			MAX-ACCESS read-only
			STATUS current
			DESCRIPTION
		        "Memory volatile capacity information.
				It is available only for DCPMM."
			::= { memoryDescriptionEntry 21 } 

		memoryPersistentCapacityMB OBJECT-TYPE
			SYNTAX INTEGER
				{
				unknown(-1)
				}
			MAX-ACCESS read-only
			STATUS current
			DESCRIPTION
		        "Memory persistent capacity information.
				It is available only for DCPMM."
			::= { memoryDescriptionEntry 22 }
			
			
--    ****** LOM(LAN on motherboard) Information *******************************
  
		lomProperty OBJECT IDENTIFIER ::= { hwiBMC 17 }    

		lomDescriptionTable OBJECT-TYPE
			SYNTAX SEQUENCE OF LOMDescriptionEntry 
			MAX-ACCESS not-accessible
			STATUS current
			DESCRIPTION
				"A table containing the LOM."
			::= { lomProperty 50 }
        
                lomDescriptionEntry OBJECT-TYPE
			SYNTAX LOMDescriptionEntry
			MAX-ACCESS not-accessible
			STATUS current
			DESCRIPTION
				"Information about LOM."
			INDEX { lomIndex }
			::= { lomDescriptionTable 1 }
		
		LOMDescriptionEntry ::=
			SEQUENCE {
				lomIndex
					INTEGER, 
				lomMACAddress
					DisplayString
				}
				 

		lomIndex OBJECT-TYPE	
			SYNTAX INTEGER
			MAX-ACCESS not-accessible
			STATUS current
			DESCRIPTION
				"Information about LOM index."
			::= { lomDescriptionEntry 1 } 
			

		lomMACAddress OBJECT-TYPE
			SYNTAX DisplayString
			MAX-ACCESS read-only
			STATUS current
			DESCRIPTION
				"Information about LOM MAC address."
			::= { lomDescriptionEntry 2 }


--    ****** HardDisk Information *******************************
  
		hardDiskProperty OBJECT IDENTIFIER ::= { hwiBMC 18 }
		

		hardDiskEntireStatus OBJECT-TYPE
			SYNTAX INTEGER 
				{
				ok(1),
				minor(2),
				major(3),
				critical(4),
				absence(5),
				unknown(6)
				}
			MAX-ACCESS read-only
			STATUS current
			DESCRIPTION
				"Information about all hard disk health status."
			::= { hardDiskProperty 1 }    

		hardDiskDescriptionTable OBJECT-TYPE
			SYNTAX SEQUENCE OF HardDiskDescriptionEntry 
			MAX-ACCESS not-accessible
			STATUS current
			DESCRIPTION
				"A table containing the hard disk."
			::= { hardDiskProperty 50 }
        
                hardDiskDescriptionEntry OBJECT-TYPE
			SYNTAX HardDiskDescriptionEntry 
			MAX-ACCESS not-accessible
			STATUS current
			DESCRIPTION
				"Information about hard disk."
			INDEX { hardDiskIndex }
			::= { hardDiskDescriptionTable 1 }
		
		HardDiskDescriptionEntry ::=
			SEQUENCE {
				hardDiskIndex
					INTEGER, 
				hardDiskPresence
					INTEGER,
				hardDiskStatus
					INTEGER,
				hardDiskLocation
					DisplayString, 
				hardDiskFunction
					DisplayString,
				hardDiskDevicename
					DisplayString,
				hardDiskSerialNumber
					DisplayString,	
				hardDiskModelNumber
					DisplayString,	
				hardDiskManufacturer
					DisplayString,
				hardDiskFwState
					INTEGER,
				hardDiskFwVersion
					DisplayString,
				hardDiskCapacityInGB
					INTEGER,
				hardDiskMediaType
					INTEGER,
				hardDiskInterfaceType
					INTEGER,
				hardDiskPowerState
					INTEGER,
				hardDiskRebuildProgress
					INTEGER,
				hardDiskPatrolReadStatus
					INTEGER,
				hardDiskCapableSpeedInMbps
					INTEGER,
				hardDiskNegotiatedSpeedInMbps
					INTEGER,
				hardDiskTemperature
					INTEGER,
				hardDiskSASAddr1
					DisplayString,
				hardDiskSASAddr2
					DisplayString,
				hardDiskPrefailState
					INTEGER,
				hardDiskHotSpareState
					INTEGER,
				hardDiskRemnantWearout
					INTEGER,
				hardDiskMediaErrCount
					INTEGER,
				hardDiskPrefailErrCount
					INTEGER,
				hardDiskOtherErrCount
					INTEGER,
				hardDiskLocationState
					INTEGER,
				hardDiskCapacityInMB
					INTEGER,
				hardDiskPowerOnHours
					INTEGER,
				hardDiskCryptoErase
					INTEGER
				}

		hardDiskIndex OBJECT-TYPE	
			SYNTAX INTEGER
			MAX-ACCESS not-accessible
			STATUS current
			DESCRIPTION
				"Information about hard disk index."
			::= { hardDiskDescriptionEntry 1 } 
			

		hardDiskPresence OBJECT-TYPE
			SYNTAX INTEGER
				{
				absence(1),
				presence(2),
				unknown(3)
				}
			MAX-ACCESS read-only
			STATUS current
			DESCRIPTION
				"Information about hard disk presence."
			::= { hardDiskDescriptionEntry 2 }


		hardDiskStatus OBJECT-TYPE
			SYNTAX INTEGER 
				{
				ok(1),
				minor(2),
				major(3),
				critical(4),
				absence(5),
				unknown(6)
				}
			MAX-ACCESS read-only
			STATUS current
			DESCRIPTION
				"Information about hard disk health."
			::= { hardDiskDescriptionEntry 3 }  

		hardDiskLocation OBJECT-TYPE	
			SYNTAX DisplayString
			MAX-ACCESS read-only
			STATUS current
			DESCRIPTION
				"Hard disk physical location."
			::= { hardDiskDescriptionEntry 4 } 

		
		hardDiskFunction OBJECT-TYPE	
			SYNTAX DisplayString
			MAX-ACCESS read-only
			STATUS current
			DESCRIPTION
				"Hard disk logic function."
			::= { hardDiskDescriptionEntry 5 } 

		
		hardDiskDevicename OBJECT-TYPE	
			SYNTAX DisplayString
			MAX-ACCESS read-only
			STATUS current
			DESCRIPTION
				"Hard disk devicename."
			::= { hardDiskDescriptionEntry 6 } 		

		hardDiskSerialNumber OBJECT-TYPE	
			SYNTAX DisplayString
			MAX-ACCESS read-only
			STATUS current
			DESCRIPTION
				"Hard disk serial number."
			::= { hardDiskDescriptionEntry 7 } 			

		hardDiskModelNumber OBJECT-TYPE	
			SYNTAX DisplayString
			MAX-ACCESS read-only
			STATUS current
			DESCRIPTION
				"Hard disk model number."
			::= { hardDiskDescriptionEntry 8 } 			

		hardDiskManufacturer OBJECT-TYPE	
			SYNTAX DisplayString
			MAX-ACCESS read-only
			STATUS current
			DESCRIPTION
				"Hard disk manufacturer."
			::= { hardDiskDescriptionEntry 9 }  
	
		hardDiskFwState OBJECT-TYPE	
			SYNTAX INTEGER 
				{
				unconfigured-good(1),
				unconfigured-bad(2),
				hot-spare(3),
				offline(4),
				failed(5),
				rebuild(6),
				online(7),
				copyback(8),
				jbod(9),
				unconfigured-shielded(10),
				hot-spare-shielded(11),
				configured-shielded(12),
				foreign(13),
				active(14),
				standby(15),
				sleep(16),
				dst(17),
				smart(18),
				sct(19),
				unknown(255)				
				}
			MAX-ACCESS read-write
			STATUS current
			DESCRIPTION
				"Hard disk firmware state.
				1: Unconfigured Good
				   Can be set from Unconfigured Bad state, or JBOD state when raidControllerJBODEnable = Enabled.
				2: Unconfigured Bad (read only)
				3: Hot Spared (read only)
				4: Offline
				   Can be set from Online state.
				5: Failed (read only)
				6: Rebuild (read only)
				7: Online
				   Can be set from Offline state.
				8: Copyback (read only)
				9: JBOD
				   Can be set from Unconfigured Good state when raidControllerJBODEnable = Enabled.
				10: Unconfigured Shielded (read only)
				11: Hot Spare Shielded (read only)
				12: Configured Shielded (read only)
				13: Foreign (read only)
				14: Active (read only)
				15: Stand-by (read only)
				16: Sleep (read only)
				17: DST executing in background (read only)
				18: SMART Off-line Data Collection executing in background (read only)
				19: SCT command executing in background (read only)				
				255: Unknown (read only)"
			::= { hardDiskDescriptionEntry 10 } 	
	
		hardDiskFwVersion OBJECT-TYPE	
			SYNTAX DisplayString 
			MAX-ACCESS read-only
			STATUS current
			DESCRIPTION
				"Hard disk firmware version."
			::= { hardDiskDescriptionEntry 11 } 	
	
		hardDiskCapacityInGB OBJECT-TYPE	
			SYNTAX INTEGER 
				{
				unknown(4294967295)
				}
			MAX-ACCESS read-only
			STATUS current
			DESCRIPTION
				"Hard disk capacity (GB)."
			::= { hardDiskDescriptionEntry 12 } 
	
		hardDiskMediaType OBJECT-TYPE	
			SYNTAX INTEGER 
				{
				hdd(1),
				ssd(2),
				ssm(3),
				unknown(255)
				}
			MAX-ACCESS read-only
			STATUS current
			DESCRIPTION
				"Hard disk media type."
			::= { hardDiskDescriptionEntry 13 } 	
	
		hardDiskInterfaceType OBJECT-TYPE	
			SYNTAX INTEGER 
				{
				undefined(1),
				parallel-scsi(2),
				sas(3),
				sata(4),
				fiber-channel(5),
				sata-sas(6),
				pcie(7),
				unknown(255)
				}
			MAX-ACCESS read-only
			STATUS current
			DESCRIPTION
				"Hard disk interface type. SAS, SATA...etc.
				1: Undefined
				2: Parallel-SCSI
				3: SAS
				4: SATA
				5: Fiber Channel
				6: SATA/SAS
				7: PCIe
				255: Unknown"
			::= { hardDiskDescriptionEntry 14 }	
	
		hardDiskPowerState OBJECT-TYPE	
			SYNTAX INTEGER 
				{
				spun-up(1),
				spun-down(2),
				transition(3),
				unknown(255)
				}
			MAX-ACCESS read-only
			STATUS current
			DESCRIPTION
				"Hard disk power state."
			::= { hardDiskDescriptionEntry 15 }
	
		hardDiskRebuildProgress OBJECT-TYPE	
			SYNTAX INTEGER 
				{
				unknown(255)
				}
			MAX-ACCESS read-only
			STATUS current
			DESCRIPTION
				"Hard disk rebuild progress (0 - 100%)."
			::= { hardDiskDescriptionEntry 16 }	
			
		hardDiskPatrolReadStatus OBJECT-TYPE	
			SYNTAX INTEGER 
				{
				stopped(1),
				in-progress(2),
				unknown(255)
				}
			MAX-ACCESS read-only
			STATUS current
			DESCRIPTION
				"Hard disk patrol read status."
			::= { hardDiskDescriptionEntry 17 }				
	
		hardDiskCapableSpeedInMbps OBJECT-TYPE	
			SYNTAX INTEGER 
				{
				unknown(4294967295)
				}
			MAX-ACCESS read-only
			STATUS current
			DESCRIPTION
				"Hard disk maximum supported speed."
			::= { hardDiskDescriptionEntry 18 }		
	
		hardDiskNegotiatedSpeedInMbps OBJECT-TYPE	
			SYNTAX INTEGER 
				{
				unknown(4294967295)
				}
			MAX-ACCESS read-only
			STATUS current
			DESCRIPTION
				"Hard disk negotiated speed."
			::= { hardDiskDescriptionEntry 19 }		
	
		hardDiskTemperature OBJECT-TYPE	
			SYNTAX INTEGER 
				{
				unknown(255)
				}
			MAX-ACCESS read-only
			STATUS current
			DESCRIPTION
				"Hard disk temperature (in Celsius)."
			::= { hardDiskDescriptionEntry 20 }		
	
		hardDiskSASAddr1 OBJECT-TYPE	
			SYNTAX DisplayString 
			MAX-ACCESS read-only
			STATUS current
			DESCRIPTION
				"Hard disk SAS address 1."
			::= { hardDiskDescriptionEntry 21 }
	
		hardDiskSASAddr2 OBJECT-TYPE	
			SYNTAX DisplayString 
			MAX-ACCESS read-only
			STATUS current
			DESCRIPTION
				"Hard disk SAS address 2."
			::= { hardDiskDescriptionEntry 22 }	
	
		hardDiskPrefailState OBJECT-TYPE	
			SYNTAX INTEGER 
				{
				no(1),
				yes(2),
				unknown(255)
				}
			MAX-ACCESS read-only
			STATUS current
			DESCRIPTION
				"Hard disk prefail state."
			::= { hardDiskDescriptionEntry 23 }	
	
		hardDiskHotSpareState OBJECT-TYPE	
			SYNTAX INTEGER 
				{
				none(1),
				global(2),
				dedicated(3),
				commissioned(4),
				emergency(5),
				unknown(255)
				}
			MAX-ACCESS read-write
			STATUS current
			DESCRIPTION
				"Hard disk hot spare state.
				1: None
				   Cancel the global/dedicated hot spare setting, can be set when hardDiskHotSpareState is Global/Dedicated.
				2: Global
				   Can be set only when hardDiskFwState = Unconfigured Good.
				3: Dedicated
				   Can be set only when hardDiskFwState = Unconfigured Good.
				   
				   Setting value described as following:
				   Byte1 - Indicating the hard disk used as dedicated hot spare, fixed to 3.
				   Byte2 - The logical drive index which the hard disk spared for, started from 1.
				   				   
				   For example:
				   Set this hard disk as dedicated hot spare for logical drive 2, the setting value should be
				   0x0203 = 2 * 256 + 3 = 515.
				4: Commissioned (read only)
				5: Emergency (read only)
				255: Unknown (read only)"
			::= { hardDiskDescriptionEntry 24 }		
	
		hardDiskRemnantWearout OBJECT-TYPE	
			SYNTAX INTEGER 
				{
				unknown(255)
				}
			MAX-ACCESS read-only
			STATUS current
			DESCRIPTION
				"Hard disk remnant wearout (100% - 0). Only valid for SSD."
			::= { hardDiskDescriptionEntry 25 }
			
		hardDiskMediaErrCount OBJECT-TYPE	
			SYNTAX INTEGER 
				{
				unknown(4294967295)
				}
			MAX-ACCESS read-only
			STATUS current
			DESCRIPTION
				"Hard disk media error count."
			::= { hardDiskDescriptionEntry 26 }			
			
		hardDiskPrefailErrCount OBJECT-TYPE	
			SYNTAX INTEGER 
				{
				unknown(4294967295)
				}
			MAX-ACCESS read-only
			STATUS current
			DESCRIPTION
				"Hard disk prefail error count."
			::= { hardDiskDescriptionEntry 27 }		
	
		hardDiskOtherErrCount OBJECT-TYPE	
			SYNTAX INTEGER 
				{
				unknown(4294967295)
				}
			MAX-ACCESS read-only
			STATUS current
			DESCRIPTION
				"Hard disk other error count."
			::= { hardDiskDescriptionEntry 28 }		
	
		hardDiskLocationState OBJECT-TYPE	
			SYNTAX INTEGER 
				{
				unknown(1),
				off(2),
				on(3)
				}
			MAX-ACCESS read-write
			STATUS current
			DESCRIPTION
				"Hard disk location state.
				1: Unknown (read only)
				2: Off
				3: On"
			::= { hardDiskDescriptionEntry 29 }
			
		hardDiskCapacityInMB OBJECT-TYPE	
			SYNTAX INTEGER 
				{
				unknown(4294967295)
				}
			MAX-ACCESS read-only
			STATUS current
			DESCRIPTION
				"Hard disk capacity (MB)."
			::= { hardDiskDescriptionEntry 30 } 

		hardDiskPowerOnHours OBJECT-TYPE	
			SYNTAX INTEGER 
				{
				unknown(-1)
				}
			MAX-ACCESS read-only
			STATUS current
			DESCRIPTION
				"Power-On Hours."
			::= { hardDiskDescriptionEntry 31 } 
		
		hardDiskCryptoErase OBJECT-TYPE
			SYNTAX INTEGER			
			MAX-ACCESS read-write
			STATUS current
			DESCRIPTION
				"Cryptographically erase a self-enrypting drive (SED) which supports Instant Secure Erase (ISE) (write only). The argument is:
				1: Self-Enrypting Drive.
				others: invalid"
			::= { hardDiskDescriptionEntry 32 }
	
--    ****** fru Product information Location *******************************
		fruInfo OBJECT IDENTIFIER ::= { hwiBMC 19 }    

		fruDescriptionTable OBJECT-TYPE
			SYNTAX SEQUENCE OF FruDescriptionEntry 
			MAX-ACCESS not-accessible
			STATUS current
			DESCRIPTION
				"A table containing the FRU information."
			::= { fruInfo 50 }
        
                fruDescriptionEntry OBJECT-TYPE
			SYNTAX FruDescriptionEntry 
			MAX-ACCESS not-accessible
			STATUS current
			DESCRIPTION
				"Information about FRU information."
			INDEX { fruId }
			::= { fruDescriptionTable 1 }
		
		FruDescriptionEntry ::=
			SEQUENCE {
				fruId
					INTEGER, 
				fruBoardManufacturer
					DisplayString,
				fruBoardProductName 
					DisplayString,
				fruBoardSerialNumber  
					DisplayString,
				fruBoardPartNumber  
					DisplayString, 
				fruBoardMfgDate    
					DisplayString,
				fruBoardFileID
					DisplayString, 
				fruProductManufacturer    
					DisplayString, 
				fruProductName    
					DisplayString, 					
				fruProductSerialNumber    
					DisplayString,					
				fruProductPartNumber    
					DisplayString,					
				fruProductVersion
					DisplayString,
				fruProductAssetTag										
					DisplayString,
				fruProductFileID
					DisplayString	
				}
				 

		fruId OBJECT-TYPE	
			SYNTAX INTEGER
			MAX-ACCESS not-accessible
			STATUS current
			DESCRIPTION
				"Information about FRU id."
			::= { fruDescriptionEntry 1 } 
			

		fruBoardManufacturer OBJECT-TYPE
			SYNTAX DisplayString
			MAX-ACCESS read-only
			STATUS current
			DESCRIPTION
				"FRU board manufacturer."
			::= { fruDescriptionEntry 2 }


		fruBoardProductName OBJECT-TYPE
			SYNTAX DisplayString
			MAX-ACCESS read-only
			STATUS current
			DESCRIPTION
				"FRU board product name."
			::= { fruDescriptionEntry 3 }  
 

		fruBoardSerialNumber OBJECT-TYPE
			SYNTAX DisplayString
			MAX-ACCESS read-only
			STATUS current
			DESCRIPTION
				"FRU board serial number."
			::= { fruDescriptionEntry 4 } 			


		fruBoardPartNumber OBJECT-TYPE
			SYNTAX DisplayString
			MAX-ACCESS read-only
			STATUS current
			DESCRIPTION
				"FRU board part number."
			::= { fruDescriptionEntry 5 } 			


		fruBoardMfgDate OBJECT-TYPE
			SYNTAX DisplayString
			MAX-ACCESS read-only
			STATUS current
			DESCRIPTION
				"FRU borad maufacturer date."
			::= { fruDescriptionEntry 6 } 			
 

		fruBoardFileID OBJECT-TYPE
			SYNTAX DisplayString
			MAX-ACCESS read-only
			STATUS current
			DESCRIPTION
				"FRU board file id."
			::= { fruDescriptionEntry 7 }  			


		fruProductManufacturer OBJECT-TYPE
			SYNTAX DisplayString
			MAX-ACCESS read-only
			STATUS current
			DESCRIPTION
				"FRU product maufacturer."
			::= { fruDescriptionEntry 8 } 


		fruProductName OBJECT-TYPE
			SYNTAX DisplayString
			MAX-ACCESS read-only
			STATUS current
			DESCRIPTION
				"FRU product name."
			::= { fruDescriptionEntry 9 } 


		fruProductSerialNumber OBJECT-TYPE
			SYNTAX DisplayString
			MAX-ACCESS read-only
			STATUS current
			DESCRIPTION
				"FRU product serial number."
			::= { fruDescriptionEntry 10 } 
			

		fruProductPartNumber OBJECT-TYPE
			SYNTAX DisplayString
			MAX-ACCESS read-only
			STATUS current
			DESCRIPTION
				"FRU product part number ."
			::= { fruDescriptionEntry 11 } 
			

		fruProductVersion OBJECT-TYPE
			SYNTAX DisplayString
			MAX-ACCESS read-only
			STATUS current
			DESCRIPTION
				"FRU product version."
			::= { fruDescriptionEntry 12 } 


		fruProductAssetTag OBJECT-TYPE
			SYNTAX DisplayString
			MAX-ACCESS read-write
			STATUS current
			DESCRIPTION
				"FRU product asset tag.
				 The value define as: A string of up to 48 bytes, including digits, letters, and special characters."
			::= { fruDescriptionEntry 13 } 


		fruProductFileID OBJECT-TYPE
			SYNTAX DisplayString
			MAX-ACCESS read-only
			STATUS current
			DESCRIPTION
				"FRU product file id."
			::= { fruDescriptionEntry 14 } 


		fruExtendedELabelDescriptionTable OBJECT-TYPE
			SYNTAX SEQUENCE OF FruExtendedELabelDescriptionEntry 
			MAX-ACCESS not-accessible
			STATUS current
			DESCRIPTION
				"A table containing the FRU extend E-label."
			::= { fruInfo 60 }
        
               fruExtendedELabelDescriptionEntry OBJECT-TYPE
			SYNTAX FruExtendedELabelDescriptionEntry 
			MAX-ACCESS not-accessible
			STATUS current
			DESCRIPTION
				"Information about label."
			INDEX { fruid,fruExtendedELabelIndex }
			::= { fruExtendedELabelDescriptionTable 1 }
		
		FruExtendedELabelDescriptionEntry ::=
			SEQUENCE {
			    fruid
			        INTEGER,
				fruExtendedELabelIndex
					INTEGER, 
				fruExtendedELabelInfo
					DisplayString
				} 
	

		fruid OBJECT-TYPE
			SYNTAX INTEGER
			MAX-ACCESS not-accessible
			STATUS current
			DESCRIPTION
				"Extened fru ID."
			::= { fruExtendedELabelDescriptionEntry 1 }
			
						

		fruExtendedELabelIndex OBJECT-TYPE
			SYNTAX INTEGER
			MAX-ACCESS read-only
			STATUS current
			DESCRIPTION
				"Fru extend E-label index."
			::= { fruExtendedELabelDescriptionEntry 2 } 


		fruExtendedELabelInfo OBJECT-TYPE
			SYNTAX DisplayString
			MAX-ACCESS read-only
			STATUS current
			DESCRIPTION
				"format: key=value"
			::= { fruExtendedELabelDescriptionEntry 3 } 


--    ****** powerStatistic Information *******************************
  
		powerStatistic OBJECT IDENTIFIER ::= { hwiBMC 20 }
			

		peakPower OBJECT-TYPE
			SYNTAX DisplayString
			MAX-ACCESS read-only
			STATUS current
			DESCRIPTION
				"System peak power, unit is W."
			::= { powerStatistic 1 }
			

		peakPowerOccurTime OBJECT-TYPE
			SYNTAX DisplayString
			MAX-ACCESS read-only
			STATUS current
			DESCRIPTION
				"System peak power occur time, based on UTC"
			::= { powerStatistic 2 } 
			

		averagePower OBJECT-TYPE
			SYNTAX DisplayString
			MAX-ACCESS read-only
			STATUS current
			DESCRIPTION
				"System average power, unit is W."
			::= { powerStatistic 3 }
		

		powerConsumption OBJECT-TYPE
			SYNTAX DisplayString
			MAX-ACCESS read-only
			STATUS current
			DESCRIPTION
				"Power consume from power statistic start time, unit is kWh."
			::= { powerStatistic 4 }
		

		powerStatisticStartTime OBJECT-TYPE
			SYNTAX DisplayString
			MAX-ACCESS read-only
			STATUS current
			DESCRIPTION
				"The start time of power statistic, based on UTC.
				the value such as (yyyy-mm-dd hh:mm:ss)."
			::= { powerStatistic 5 }
		

		clearPowerStatistic OBJECT-TYPE
			SYNTAX INTEGER
			        {
			        clearall(1)
			        }			   
			MAX-ACCESS read-write
			STATUS current
			DESCRIPTION
				"clear all power statistic, write only."
			::= { powerStatistic 6 }
			
		heat OBJECT-TYPE
			SYNTAX INTEGER
			MAX-ACCESS read-only
			STATUS current
			DESCRIPTION
				"Heat consume from power statistic start time, unit is kcal."
			::= { powerStatistic 7 }
			                                                              
			                                                              
--    ****** powerManagement Information *******************************
  
		powerManagement OBJECT IDENTIFIER ::= { hwiBMC 23 }           
			

		powerCappingEnable OBJECT-TYPE
			SYNTAX INTEGER
				{
				disable(1),
				enable(2)
				}
			MAX-ACCESS read-write
			STATUS current
			DESCRIPTION
				"Power capping status. disable 1, enable 2.
				Default value is disable(1)."
			::= { powerManagement 1 }
			

		powerCappingValue OBJECT-TYPE
			SYNTAX INTEGER
			MAX-ACCESS read-write
			STATUS current
			DESCRIPTION
				"Power capping value, the vaule is in [1, 9999]."
			::= { powerManagement 2 } 
			

		powerCappingFailureAction OBJECT-TYPE
			SYNTAX INTEGER           
				{
				eventlog(1),				                               
				eventlogAndPowerOff(2)				
				}
			MAX-ACCESS read-write
			STATUS current
			DESCRIPTION
				"When power capping failed, host system action.
				Default value is eventlog(1)."
			::= { powerManagement 3 }


		pCIeDeviceProperty OBJECT IDENTIFIER ::= { hwiBMC 24 } 
 
 		pCIeDeviceEntireStatus OBJECT-TYPE
			SYNTAX INTEGER 
				{
				ok(1),
				minor(2),
				major(3),
				critical(4),
				absence(5),
				unknown(6)
				}
			MAX-ACCESS read-only
			STATUS current
			DESCRIPTION
				"Information about all standard PCIe device health status."
			::= { pCIeDeviceProperty 1 }
			
		pCIeDeviceMaxNum OBJECT-TYPE
			SYNTAX INTEGER 
			MAX-ACCESS read-only
			STATUS current
			DESCRIPTION
				"Max number of PCIe devices."
			::= { pCIeDeviceProperty 2 }
 
		pCIeDeviceDescriptionTable OBJECT-TYPE
			SYNTAX SEQUENCE OF PCIeDeviceDescriptionEntry 
			MAX-ACCESS not-accessible
			STATUS current
			DESCRIPTION
				"A table containing the standard PCIe device."
			::= { pCIeDeviceProperty 50 }
        
                pCIeDeviceDescriptionEntry OBJECT-TYPE
			SYNTAX PCIeDeviceDescriptionEntry 
			MAX-ACCESS not-accessible
			STATUS current
			DESCRIPTION
				"Information about PCIe device."
			INDEX { pCIeDeviceIndex }
			::= { pCIeDeviceDescriptionTable 1 }
		
		PCIeDeviceDescriptionEntry ::=
			SEQUENCE {
				pCIeDeviceIndex
					INTEGER, 
				pCIeDevicePresence
					INTEGER,
				pCIeDeviceStatus
					INTEGER,
				pCIeAvailability
				    INTEGER,
				pCIeDeviceLocation
				    DisplayString,
				pCIeDeviceFunction
				    DisplayString,
				pCIeDeviceDevicename
				    DisplayString,
				pCIeDeviceVID
				    INTEGER,
				pCIeDeviceDID
				    INTEGER,
				pCIeDeviceManufacturer
				    DisplayString,
				pCIeDeviceDescription
				    DisplayString
				}
				 
		
		pCIeDeviceIndex OBJECT-TYPE	
			SYNTAX INTEGER
			MAX-ACCESS not-accessible
			STATUS current
			DESCRIPTION
				"Information about PCIe device index."
			::= { pCIeDeviceDescriptionEntry 1 } 
					
		
		pCIeDevicePresence OBJECT-TYPE
			SYNTAX INTEGER
				{
				absence(1),
				presence(2),
				unknown(3)
				}
			MAX-ACCESS read-only
			STATUS current
			DESCRIPTION
				"Information about PCIe device presence."
			::= { pCIeDeviceDescriptionEntry 2 }

		
		pCIeDeviceStatus OBJECT-TYPE
			SYNTAX INTEGER 
				{
				ok(1),
				minor(2),
				major(3),
				critical(4),
				absence(5),
				unknown(6)
				}
			MAX-ACCESS read-only
			STATUS current
			DESCRIPTION
				"Information about PCIe device health."
			::= { pCIeDeviceDescriptionEntry 3 }  
			
			   
         pCIeAvailability OBJECT-TYPE
            SYNTAX INTEGER 
                 {
                 unknown(1),
                 disabled(2),
                 backup(3),
                 active(4)
                 }
            MAX-ACCESS read-only
            STATUS current
            DESCRIPTION
            "Information about PCIe device availability."
            ::= { pCIeDeviceDescriptionEntry 4 }
					
		pCIeDeviceLocation OBJECT-TYPE
			SYNTAX DisplayString
			MAX-ACCESS read-only
			STATUS current
			DESCRIPTION
				" PCIe physical location."
			::= { pCIeDeviceDescriptionEntry 5 }

		
		pCIeDeviceFunction OBJECT-TYPE
			SYNTAX DisplayString
			MAX-ACCESS read-only
			STATUS current
			DESCRIPTION
				" PCIe logic function."
			::= { pCIeDeviceDescriptionEntry 6 }  
 
		
		pCIeDeviceDevicename OBJECT-TYPE
			SYNTAX DisplayString
			MAX-ACCESS read-only
			STATUS current
			DESCRIPTION
				" PCIe devicename."
			::= { pCIeDeviceDescriptionEntry 7 } 

		pCIeDeviceVID OBJECT-TYPE	
			SYNTAX INTEGER
			MAX-ACCESS read-only
			STATUS current
			DESCRIPTION
				"PCIe device VID."
			::= { pCIeDeviceDescriptionEntry 8 } 
			
		pCIeDeviceDID OBJECT-TYPE	
			SYNTAX INTEGER
			MAX-ACCESS read-only
			STATUS current
			DESCRIPTION
				"PCIe device DID."
			::= { pCIeDeviceDescriptionEntry 9 } 
			
		pCIeDeviceManufacturer OBJECT-TYPE
			SYNTAX DisplayString
			MAX-ACCESS read-only
			STATUS current
			DESCRIPTION
				" PCIe device manufacturer."
			::= { pCIeDeviceDescriptionEntry 10 }  
			
		pCIeDeviceDescription OBJECT-TYPE
			SYNTAX DisplayString
			MAX-ACCESS read-only
			STATUS current
			DESCRIPTION
				" PCIe device description."
			::= { pCIeDeviceDescriptionEntry 11 } 
			                        

		netCardProperty OBJECT IDENTIFIER ::= { hwiBMC 25 }    

		netCardDescriptionTable OBJECT-TYPE
			SYNTAX SEQUENCE OF NetCardDescriptionEntry 
			MAX-ACCESS not-accessible
			STATUS current
			DESCRIPTION
				"A table containing the net card information."
			::= { netCardProperty 50 }
        
            netCardDescriptionEntry  OBJECT-TYPE
			SYNTAX NetCardDescriptionEntry 
			MAX-ACCESS not-accessible
			STATUS current
			DESCRIPTION
				"Information about net card."
			INDEX { netCardIndex }
			::= { netCardDescriptionTable 1 }
		
		NetCardDescriptionEntry  ::=
			SEQUENCE {
				netCardIndex
					INTEGER,
				netCardLocation
					DisplayString,
				netCardFunction 
					DisplayString,
				netCardDevicename
					DisplayString,
				netCardNICModel
					DisplayString,
				netCardNICType
					INTEGER,
				netCardNICName
					DisplayString,
				netCardChipModel
					DisplayString,
				netCardNICManufacturer
					DisplayString,
				netCardChipManufacturer
					DisplayString,
				netCardDriverName
					DisplayString,
				netCardDriverVersion
					DisplayString,
				netCardFirmwareVersion
					DisplayString,
				netCardPCBVersion
					DisplayString,
				netCardBoardId
					INTEGER,
				netCardResourceOwnership
					INTEGER,
				netCardRootBDF
					DisplayString,
				netCardStatus
				    INTEGER
				}
				 
		
		netCardIndex OBJECT-TYPE	
			SYNTAX INTEGER
			MAX-ACCESS not-accessible
			STATUS current
			DESCRIPTION
				" Information about net card index."
			::= { netCardDescriptionEntry 1 } 
			
		
		netCardLocation OBJECT-TYPE
			SYNTAX DisplayString
			MAX-ACCESS read-only
			STATUS current
			DESCRIPTION
				" Net card physical location."
			::= { netCardDescriptionEntry 2 }

		
		netCardFunction OBJECT-TYPE
			SYNTAX DisplayString
			MAX-ACCESS read-only
			STATUS current
			DESCRIPTION
				" Net card logic function."
			::= { netCardDescriptionEntry 3 }  
 
		
		netCardDevicename OBJECT-TYPE
			SYNTAX DisplayString
			MAX-ACCESS read-only
			STATUS current
			DESCRIPTION
				" Net card device name."
			::= { netCardDescriptionEntry 4 }
			
		netCardNICModel OBJECT-TYPE
			SYNTAX DisplayString
			MAX-ACCESS read-only
			STATUS current
			DESCRIPTION
				" Net card model."
			::= { netCardDescriptionEntry 5 }

		netCardNICType OBJECT-TYPE
			SYNTAX INTEGER
			{
				pcieCard (8),
				mezzCard (11),
				nic (13)
			}
			MAX-ACCESS read-only
			STATUS current
			DESCRIPTION
				" NIC type define as:
				  8: PCIe card, 
				  11: Mezz card,
				  13: NIC."
			::= { netCardDescriptionEntry 6 }

		netCardNICName OBJECT-TYPE
			SYNTAX DisplayString
			MAX-ACCESS read-only
			STATUS current
			DESCRIPTION
				" Net card name."
			::= { netCardDescriptionEntry 7 }

		netCardChipModel OBJECT-TYPE
			SYNTAX DisplayString
			MAX-ACCESS read-only
			STATUS current
			DESCRIPTION
				" Net card chip model."
			::= { netCardDescriptionEntry 8 }

		netCardNICManufacturer OBJECT-TYPE
			SYNTAX DisplayString
			MAX-ACCESS read-only
			STATUS current
			DESCRIPTION
				" Net card manufacturer."
			::= { netCardDescriptionEntry 9 }

		netCardChipManufacturer OBJECT-TYPE
			SYNTAX DisplayString
			MAX-ACCESS read-only
			STATUS current
			DESCRIPTION
				" Net card chip manufacturer."
			::= { netCardDescriptionEntry 10 }

		netCardDriverName OBJECT-TYPE
			SYNTAX DisplayString
			MAX-ACCESS read-only
			STATUS current
			DESCRIPTION
				" Net card driver name."
			::= { netCardDescriptionEntry 11 }

		netCardDriverVersion OBJECT-TYPE
			SYNTAX DisplayString
			MAX-ACCESS read-only
			STATUS current
			DESCRIPTION
				" Net card driver version."
			::= { netCardDescriptionEntry 12 }

		netCardFirmwareVersion OBJECT-TYPE
			SYNTAX DisplayString
			MAX-ACCESS read-only
			STATUS current
			DESCRIPTION
				" Net card firmware version."
			::= { netCardDescriptionEntry 13 }

		netCardPCBVersion OBJECT-TYPE
			SYNTAX DisplayString
			MAX-ACCESS read-only
			STATUS current
			DESCRIPTION
				" Net card PCB version."
			::= { netCardDescriptionEntry 14 }

		netCardBoardId OBJECT-TYPE
			SYNTAX INTEGER
			{
				unknown(-1)
			}
			MAX-ACCESS read-only
			STATUS current
			DESCRIPTION
				" Net card board ID."
			::= { netCardDescriptionEntry 15 }

		netCardResourceOwnership OBJECT-TYPE
			SYNTAX INTEGER
			{
				pch (254),
				pcieSwitch (255)
			}
			MAX-ACCESS read-only
			STATUS current
			DESCRIPTION
				" Net card resource ownership.
				  The value n is defined as:
				  1~253: CPU[n], 
				  254: PCH,
				  255: PCIe Switch."
			::= { netCardDescriptionEntry 16 }

		netCardRootBDF OBJECT-TYPE
			SYNTAX DisplayString
			MAX-ACCESS read-only
			STATUS current
			DESCRIPTION
				" Net card root port BDF."
			::= { netCardDescriptionEntry 17 }
			
		netCardStatus OBJECT-TYPE
			SYNTAX INTEGER 
				{
				ok(1),
				minor(2),
				major(3),
				critical(4)
				}
			MAX-ACCESS read-only
			STATUS current
			DESCRIPTION
				"Net card health status."
			::= { netCardDescriptionEntry 18 }
			
	 temperatureProperty OBJECT IDENTIFIER ::= { hwiBMC 26 } 
	
	temperatureEntireStatus OBJECT-TYPE
	SYNTAX INTEGER 
		{
		ok(1),
		minor(2),
		major(3),
		critical(4),
		unknow(5)
		}
	MAX-ACCESS read-only
	STATUS current
	DESCRIPTION
		"Information about all temperature sensor health status."
	::= { temperatureProperty 1 }
	
	 temperatureDescriptionTable OBJECT-TYPE
			SYNTAX SEQUENCE OF TemperatureDescriptionEntry 
			MAX-ACCESS not-accessible
			STATUS current
			DESCRIPTION
				"A table containing the temperature infomation."
			::= { temperatureProperty 50 }
        
            temperatureDescriptionEntry  OBJECT-TYPE
			SYNTAX TemperatureDescriptionEntry 
			MAX-ACCESS not-accessible
			STATUS current
			DESCRIPTION
				"Information about temperature."
			INDEX { temperatureIndex }
			::= { temperatureDescriptionTable 1 }
		
		TemperatureDescriptionEntry  ::=
			SEQUENCE {
				temperatureIndex
					INTEGER,
				temperatureObject
					DisplayString,
				temperatureReading 
					INTEGER,
				temperatureUpperNonRecoverable
					INTEGER,
				temperatureUpperCritical
					INTEGER,
				temperatureUpperMinor
					INTEGER,
				temperatureLowerNonRecoverable
					INTEGER,
				temperatureLowerCritical
					INTEGER,
				temperatureLowerMinor
					INTEGER
				}
				 
		
		temperatureIndex OBJECT-TYPE	
			SYNTAX INTEGER
			MAX-ACCESS not-accessible
			STATUS current
			DESCRIPTION
				" Information about temperature index."
			::= { temperatureDescriptionEntry 1 } 

		temperatureObject OBJECT-TYPE	
			SYNTAX DisplayString
			MAX-ACCESS read-only
			STATUS current
			DESCRIPTION
				" Information about temperature object."
			::= { temperatureDescriptionEntry 2 }  
			
		temperatureReading OBJECT-TYPE	
			SYNTAX INTEGER
			MAX-ACCESS read-only
			STATUS current
			DESCRIPTION
				" Information about temperature reading,the unit is 1/10 Celsius degree.
				If power off, the CPU temperature cannot be readable and is set to 65535."
			::= { temperatureDescriptionEntry 3 }   
			
		temperatureUpperNonRecoverable OBJECT-TYPE	
			SYNTAX INTEGER
			MAX-ACCESS read-only
			STATUS current
			DESCRIPTION
				" Information about temperature upper nonrecoverable threshold,the unit is 1/10 Celsius degree,65535 represent NA."
			::= { temperatureDescriptionEntry 4 }
			
		temperatureUpperCritical OBJECT-TYPE	
			SYNTAX INTEGER
			MAX-ACCESS read-only
			STATUS current
			DESCRIPTION
				" Information about temperature upper critical threshold,the unit is 1/10 Celsius degree,65535 represent NA."
			::= { temperatureDescriptionEntry 5 }

		temperatureUpperMinor OBJECT-TYPE	
			SYNTAX INTEGER
			MAX-ACCESS read-only
			STATUS current
			DESCRIPTION
				" Information about temperature upper minor threshold,the unit is 1/10 Celsius degree,65535 represent NA."
			::= { temperatureDescriptionEntry 6 }
			
		temperatureLowerNonRecoverable OBJECT-TYPE	
			SYNTAX INTEGER
			MAX-ACCESS read-only
			STATUS current
			DESCRIPTION
				" Information about temperature lower nonrecoverable threshold,the unit is 1/10 Celsius degree,65535 represent NA."
			::= { temperatureDescriptionEntry 7 }
			
		temperatureLowerCritical OBJECT-TYPE	
			SYNTAX INTEGER
			MAX-ACCESS read-only
			STATUS current
			DESCRIPTION
				" Information about temperature lower critical threshold,the unit is 1/10 Celsius degree,65535 represent NA."
			::= { temperatureDescriptionEntry 8 }
			
		temperatureLowerMinor OBJECT-TYPE	
			SYNTAX INTEGER
			MAX-ACCESS read-only
			STATUS current
			DESCRIPTION
				" Information about temperature lower minor threshold,the unit is 1/10 Celsius degree,65535 represent NA."
			::= { temperatureDescriptionEntry 9 }        
			
--  ****************** networkTimeProtocol information **********************		
		networkTimeProtocol OBJECT IDENTIFIER ::= { hwiBMC 27 }    

		ntpSupport OBJECT-TYPE	
			SYNTAX INTEGER
			{
				nosupport (1),
				support (2)				
			}			
			MAX-ACCESS read-only
			STATUS current
			DESCRIPTION
				"Information about whether the system support NTP.If the system does not support NTP,then we can ignore the value returned by working the nodes of networkTimeProtocol."
			::= { networkTimeProtocol 1 } 
		
		ntpEnabled OBJECT-TYPE	
			SYNTAX INTEGER
			{
				disable (1),
				enable (2)				
			}			
			MAX-ACCESS read-write
			STATUS current
			DESCRIPTION
				"Enable or disable NTP."
			::= { networkTimeProtocol 2 } 
			
		preferredNTPServer OBJECT-TYPE
			SYNTAX DisplayString
			MAX-ACCESS read-write
			STATUS current
			DESCRIPTION
				"IPv4 or IPv6 address, or domain name of the preferred NTP server.
                The value is the correct IP address or domain name. 
                The default value is a null string.
				Setting the value to 0.0.0.0 can clear the parameter value."
			::= { networkTimeProtocol 3 }
			
		alternateNTPServer OBJECT-TYPE
			SYNTAX DisplayString
			MAX-ACCESS read-write
			STATUS current
			DESCRIPTION
				"IPv4 or IPv6 address, or domain name of the alternate NTP server.
                The value is the correct IP address or domain name. 
                The default value is a null string.
				Setting the value to 0.0.0.0 can clear the parameter value."
			::= { networkTimeProtocol 4 }
			

		ntpServersource OBJECT-TYPE
			SYNTAX INTEGER
				{
				manual (1),
				auto (2)
				}
			MAX-ACCESS read-write
			STATUS current
			DESCRIPTION
				"Information about NTP source."
			::= { networkTimeProtocol 5 }						

		bindNTPIPProtocol OBJECT-TYPE
			SYNTAX INTEGER
				{
				ipv4 (1),
				ipv6 (2)
				}
			MAX-ACCESS read-write
			STATUS current
			DESCRIPTION
				"Information about NTP bind ip protocol."
			::= { networkTimeProtocol 6 }                                           
		
		ntpAuthEnabled OBJECT-TYPE	
			SYNTAX INTEGER
			{
				disable (1),
				enable (2)				
			}			
			MAX-ACCESS read-write
			STATUS current
			DESCRIPTION
				"Enable or disable NTP authentication."
			::= { networkTimeProtocol 7 }
			          
		ntpImportGroupkey OBJECT-TYPE	
			SYNTAX DisplayString			
			MAX-ACCESS read-write
			STATUS current
			DESCRIPTION 
			"Import group key." 
			::= { networkTimeProtocol 8 }
			
		ntpGroupkeyState OBJECT-TYPE
			SYNTAX INTEGER
				{
				notimported (1),
				imported (2)
				}
			MAX-ACCESS read-only
			STATUS current
			DESCRIPTION
				"Information about NTP Group key."
			::= { networkTimeProtocol 9 }

		ntpMinimumPollingInterval  OBJECT-TYPE
			SYNTAX INTEGER
				{
				interval8s (3),
				interval16s (4),
				interval32s (5),
				interval64s (6),
				interval128s (7),
				interval256s (8),
				interval512s (9),
				interval1024s (10),
				interval34m (11),
				interval68m (12),
				interval2h (13),
				interval4h (14),
				interval9h (15),
				interval18h (16),
				interval36h (17)
				}
	
			MAX-ACCESS read-write
			STATUS current
			DESCRIPTION
				"The minimum poll intervals for NTP messages, in seconds to the power of two. The value range is 3 to 17."
			::= { networkTimeProtocol 10 }

		ntpMaximumPollingInterval  OBJECT-TYPE
			SYNTAX INTEGER
				{
				interval8s (3),
				interval16s (4),
				interval32s (5),
				interval64s (6),
				interval128s (7),
				interval256s (8),
				interval512s (9),
				interval1024s (10),
				interval34m (11),
				interval68m (12),
				interval2h (13),
				interval4h (14),
				interval9h (15),
				interval18h (16),
				interval36h (17)
				}
			MAX-ACCESS read-write
			STATUS current
			DESCRIPTION
				"The maximum poll intervals for NTP messages, in seconds to the power of two.  The value range is 3 to 17."
			::= { networkTimeProtocol 11 }
			
	snmpMIBConfig OBJECT IDENTIFIER ::= { hwiBMC 29 }  
			
		snmpV3Algorithm OBJECT-TYPE	
			SYNTAX INTEGER
			{
             mD5andDES (1),
             mD5andAES (2),
             sHA1andDES (3),
             sHA1andAES (4)				
			}			
			MAX-ACCESS read-write
			STATUS current
			DESCRIPTION
				"Information about the authentication and encryption algorithm for SNMP V3.
				the format is AUTHORITYandENCRPTION: 
                MD5andDES(1),
                MD5andAES(2),
                SHA1andDES(3),
                SHA1andAES(4).                
                NOTE: the snmp will restart after this value changed.
                "
			::= { snmpMIBConfig 1 }	

	firmwareUpgrade OBJECT IDENTIFIER ::= { hwiBMC 30 }
	
	firmwareUpgradeStart OBJECT-TYPE
			SYNTAX DisplayString
			MAX-ACCESS read-write
			STATUS current
			DESCRIPTION
				"Start upgrade firmware,
				The set format is: <firmware URI>,[effect mode], with max length 256.
				The <firmware URI> format is: /PATH/FILE.   
				The [effect mode] is an optional parameter. It only refers to upgrading iBMC firmware. The definition is as following and default is 2.  
				1: manually reboot later;
				2: auto reboot after upgrade;
				In addition, This parameter is ignored in iBMC which is 2.36 and above.
				
				e.g.: /tmp/image.hpm,1.
				
				NOTE:
				1.Do not power off the server or restart the iBMC during the firmware upgrade.   
				2.If the firmware fails to upgrade, check whether the iBMC's memory capacity is sufficient and the upgrade file is correct.   
				3.Upgrade BIOS firmware, system needs two minutes of preparation time.   
				4.Do not shut down or restart the OS during a BIOS upgrade.
				5.If OS is power on,the BIOS upgrade file is uploaded to BMC and take effect when OS is power-off or reseted next time."
			::= { firmwareUpgrade 1 } 
		
	firmwareUpgradeState OBJECT-TYPE
			SYNTAX INTEGER
			MAX-ACCESS read-only
			STATUS current
			DESCRIPTION
				"Information about firmware upgrading state.
				the value defined as:
				  -1: upgrade not start or completed,
                  -2: file uploading,
                  -3: checking preUpgrade,
                  -4: invalid URI or file not exist,
                  -5: file upload failed,
                  -6: file too large or memory not enough,
                  -7: invalid upgrade package,
                  -8: not support upgrade in current state,
                  -9: upgrade failed,
                  -10: The upgrade file does not match the device to be upgraded,
                  -11: The BIOS upgrade fails because the ME status is not correct,
                  -12: Unknown error,
                  [0,100]:represents upgrade progress in percentage while firmware being upgrading."
			::= { firmwareUpgrade 2 } 
			
	firmwareUpgradeDetailedResults OBJECT-TYPE
		SYNTAX DisplayString
		MAX-ACCESS read-only
		STATUS current
		DESCRIPTION
			"Detailed results about firmware upgrade."
		::= { firmwareUpgrade 3 } 
			
--    ******* currentCertInfo Information *******************************
	certificate OBJECT IDENTIFIER ::= { hwiBMC 31 }    
	
	currentCertInfo OBJECT IDENTIFIER ::= { certificate 1 }
	  
	ownerCountry OBJECT-TYPE
			SYNTAX DisplayString
			MAX-ACCESS read-only
			STATUS current
			DESCRIPTION 
			"Owner country of current certificate, with length of 2." 
			::= { currentCertInfo 1 } 		
	
	ownerState OBJECT-TYPE
			SYNTAX DisplayString
			MAX-ACCESS read-only
			STATUS current
			DESCRIPTION 
			"Owner state of current certificate, with length of [0,64]." 
			::= { currentCertInfo 2 }   
	
	ownerLocation OBJECT-TYPE
			SYNTAX DisplayString
			MAX-ACCESS read-only
			STATUS current
			DESCRIPTION 
			"Owner location of current certificate, with length of [0,64]." 
			::= { currentCertInfo 3 } 		
	
	ownerOrganization OBJECT-TYPE
			SYNTAX DisplayString
			MAX-ACCESS read-only
			STATUS current
			DESCRIPTION 
			"Owner organization of current certificate, with length of [0,64]." 
			::= { currentCertInfo 4 }  
			
	ownerOrganizationUnit OBJECT-TYPE
			SYNTAX DisplayString
			MAX-ACCESS read-only
			STATUS current
			DESCRIPTION 
			"Owner organization unit of current certificate, with length of [0,64]." 
			::= { currentCertInfo 5 }

	ownerCommonName OBJECT-TYPE
			SYNTAX DisplayString
			MAX-ACCESS read-only
			STATUS current
			DESCRIPTION 
			"Owner common name of current certificate, with length of [1,64]." 
			::= { currentCertInfo 6 }
			
			
    issuerCountry OBJECT-TYPE
			SYNTAX DisplayString
			MAX-ACCESS read-only
			STATUS current
			DESCRIPTION 
			"Issuer country of current certificate, with length of 2." 
			::= { currentCertInfo 7 } 		
	
	issuerState OBJECT-TYPE
			SYNTAX DisplayString
			MAX-ACCESS read-only
			STATUS current
			DESCRIPTION 
			"Issuer state of current certificate, with length of [0,64]." 
			::= { currentCertInfo 8 }   
	
	issuerLocation OBJECT-TYPE
			SYNTAX DisplayString
			MAX-ACCESS read-only
			STATUS current
			DESCRIPTION 
			"Issuer location of current certificate, with length of [0,64]." 
			::= { currentCertInfo 9 } 		
	
	issuerOrganization OBJECT-TYPE
			SYNTAX DisplayString
			MAX-ACCESS read-only
			STATUS current
			DESCRIPTION 
			"Issuer organization of current certificate, with length of [0,64]." 
			::= { currentCertInfo 10 }  
			
	issuerOrganizationUnit OBJECT-TYPE
			SYNTAX DisplayString
			MAX-ACCESS read-only
			STATUS current
			DESCRIPTION 
			"Issuer organization unit of current certificate, with length of [0,64]." 
			::= { currentCertInfo 11 }

	issuerCommonName OBJECT-TYPE
			SYNTAX DisplayString
			MAX-ACCESS read-only
			STATUS current
			DESCRIPTION 
			"Issuer common name of current certificate, with length of [1,64]." 
			::= { currentCertInfo 12 }  
	
	
	certStartTime OBJECT-TYPE
			SYNTAX DisplayString
			MAX-ACCESS read-only
			STATUS current
			DESCRIPTION 
			"Start time of current certificate." 
			::= { currentCertInfo 13 }
			
	certExpiration OBJECT-TYPE
			SYNTAX DisplayString
			MAX-ACCESS read-only
			STATUS current
			DESCRIPTION 
			"Expiration of current certificate." 
			::= { currentCertInfo 14 }
	
	
	csrRequestInfo OBJECT IDENTIFIER ::= { certificate 2 } 
	
	reqCountry OBJECT-TYPE
			SYNTAX DisplayString
			MAX-ACCESS read-write
			STATUS current
			DESCRIPTION 
			"Owner country of request certificate, with length of 2, contains any letters." 
			::= { csrRequestInfo 1 } 		
	
	reqState OBJECT-TYPE
			SYNTAX DisplayString
			MAX-ACCESS read-write
			STATUS current
			DESCRIPTION 
			"Owner state of request certificate, with length of [0,64], contains any digits, letters, or the symbol spaces." 
			::= { csrRequestInfo 2 }   
	
	reqLocation OBJECT-TYPE
			SYNTAX DisplayString
			MAX-ACCESS read-write
			STATUS current
			DESCRIPTION 
			"Owner location of request certificate, with length of [0,64], contains any digits, letters, or the symbol spaces." 
			::= { csrRequestInfo 3 } 		
	
	reqOrganization OBJECT-TYPE
			SYNTAX DisplayString
			MAX-ACCESS read-write
			STATUS current
			DESCRIPTION 
			"Owner organization of request certificate, with length of [0,64], contains any digits, letters, or - _ . spaces symbol." 
			::= { csrRequestInfo 4 }  
			
	reqOrganizationUnit OBJECT-TYPE
			SYNTAX DisplayString
			MAX-ACCESS read-write
			STATUS current
			DESCRIPTION 
			"Owner organization unit of request certificate, with length of [0,64], contains any digits, letters, or - _ . spaces symbol." 
			::= { csrRequestInfo 5 }

	reqCommonName OBJECT-TYPE
			SYNTAX DisplayString
			MAX-ACCESS read-write
			STATUS current
			DESCRIPTION 
			"Owner common name of request certificate, with length of [1,64], contains any digits, letters, or - _ . spaces symbol." 
			::= { csrRequestInfo 6 }
			
	csrGenerate OBJECT-TYPE
			SYNTAX INTEGER 		
				{
				csrGenerate(1)			                               				
				}

			MAX-ACCESS read-write
			STATUS current
			DESCRIPTION 
			"Start to generate CSR of request certificate." 
			::= { csrRequestInfo 7 }
			
	csrExport OBJECT-TYPE
			SYNTAX DisplayString
			MAX-ACCESS read-only
			STATUS current
			DESCRIPTION 
			"Acquire the CSR of request certificate. The value is empty if request csr not exist." 
			::= { csrRequestInfo 8 }
			
	certificateImport OBJECT-TYPE
			SYNTAX DisplayString			
			MAX-ACCESS read-write
			STATUS current
			DESCRIPTION 
			"Import server certificate and the server certificate must be in the .pem format." 
			::= { csrRequestInfo 9 }

	csrStatus OBJECT-TYPE
			SYNTAX INTEGER
				{
				notStartedOrHasSuccessfullyCompleted (1),
				beingGenerated (2),
				failsGenerated (3)
				}
			MAX-ACCESS read-only
			STATUS current
			DESCRIPTION
				"The status of generating CSR.
				CSR generation has not started or has successfully completed(1)
				A CSR is being generated (2)
				A CSR fails to be generated (3)."
			::= { csrRequestInfo 10 }  			
			
	customCertInsert OBJECT IDENTIFIER ::= { certificate 3 }
	
	customCertificateContent OBJECT-TYPE
			SYNTAX DisplayString
			MAX-ACCESS read-write
			STATUS current
			DESCRIPTION 
			"Set custom certificate content and the custom certificate must be in the .pfx format." 
			::= { customCertInsert 1 }
			
	customCertificatePasswd OBJECT-TYPE
			SYNTAX DisplayString
			MAX-ACCESS read-write
			STATUS current
			DESCRIPTION 
			"Set custom certificate password, with max len 127." 
			::= { customCertInsert 2 }
			
	customCertificateImport OBJECT-TYPE
			SYNTAX INTEGER 
			    {
			    customCertificateImport(1)			
			    }
			MAX-ACCESS read-write
			STATUS current
			DESCRIPTION 
			"The action of import custom certificate." 
			::= { customCertInsert 3 }
                                               
	caCertInfoTable OBJECT-TYPE
		SYNTAX SEQUENCE OF CACertInfoEntry 
		MAX-ACCESS read-only
		STATUS current
		DESCRIPTION
			"A table containing the list of certificate information."
		::= { certificate 4 }
	
			caCertInfoEntry OBJECT-TYPE
		SYNTAX CACertInfoEntry
		MAX-ACCESS read-only
		STATUS current
		DESCRIPTION
			"Information about certificate."
		INDEX { caCertIndex }
		::= { caCertInfoTable 1 }	
		
		CACertInfoEntry ::=
			SEQUENCE {
			caCertIndex
				INTEGER, 
			caCertType
				DisplayString,
			caCertOwnerCountry
				DisplayString,
			caCertOwnerState 
				DisplayString, 	
			caCertOwnerLocation 
				DisplayString,
			caCertOwnerOrganization
				DisplayString,
			caCertOwnerOrganizationUnit 
				DisplayString,
			caCertOwnerCommonName 
				DisplayString, 
			caCertIssuerCountry 
				DisplayString, 
			caCertIssuerState 
				DisplayString, 					
			caCertIssuerLocation 
				DisplayString,
			caCertIssuerOrganization 
				DisplayString,
			caCertIssuerOrganizationUnit
				DisplayString,
			caCertIssuerCommonName 
				DisplayString,
			caCertStartTime
				DisplayString,
			caCertExpiration
				DisplayString,
			caCertSN
				DisplayString 
				}
				
		caCertIndex OBJECT-TYPE	
			SYNTAX INTEGER
			MAX-ACCESS read-only
			STATUS current
			DESCRIPTION
				"Information about certificate index."
			::= { caCertInfoEntry 1 } 
			
		caCertType OBJECT-TYPE
			SYNTAX DisplayString
			MAX-ACCESS read-only
			STATUS current
			DESCRIPTION 
			"Information about certificate type." 
			::= { caCertInfoEntry 2 } 	
	
		caCertOwnerCountry OBJECT-TYPE
			SYNTAX DisplayString
			MAX-ACCESS read-only
			STATUS current
			DESCRIPTION 
			"Owner country of current certificate, with length of 2." 
			::= { caCertInfoEntry 3 } 		
		
		caCertOwnerState OBJECT-TYPE
			SYNTAX DisplayString
			MAX-ACCESS read-only
			STATUS current
			DESCRIPTION 
			"Owner state of current certificate, with length of [0,64]." 
			::= { caCertInfoEntry 4 }   
	
		caCertOwnerLocation OBJECT-TYPE
			SYNTAX DisplayString
			MAX-ACCESS read-only
			STATUS current
			DESCRIPTION 
			"Owner location of current certificate, with length of [0,64]." 
			::= { caCertInfoEntry 5 } 		
		
		caCertOwnerOrganization OBJECT-TYPE
			SYNTAX DisplayString
			MAX-ACCESS read-only
			STATUS current
			DESCRIPTION 
			"Owner organization of current certificate, with length of [0,64]." 
			::= { caCertInfoEntry 6 }  
				
		caCertOwnerOrganizationUnit OBJECT-TYPE
			SYNTAX DisplayString
			MAX-ACCESS read-only
			STATUS current
			DESCRIPTION 
			"Owner organization unit of current certificate, with length of [0,64]." 
			::= { caCertInfoEntry 7 }

		caCertOwnerCommonName OBJECT-TYPE
			SYNTAX DisplayString
			MAX-ACCESS read-only
			STATUS current
			DESCRIPTION 
			"Owner common name of current certificate, with length of [1,64]." 
			::= { caCertInfoEntry 8 }
			
				
		caCertIssuerCountry OBJECT-TYPE
			SYNTAX DisplayString
			MAX-ACCESS read-only
			STATUS current
			DESCRIPTION 
			"Issuer country of current certificate, with length of 2." 
			::= { caCertInfoEntry 9 } 		
		
		caCertIssuerState OBJECT-TYPE
			SYNTAX DisplayString
			MAX-ACCESS read-only
			STATUS current
			DESCRIPTION 
			"Issuer state of current certificate, with length of [0,64]." 
			::= { caCertInfoEntry 10 }   
		
		caCertIssuerLocation OBJECT-TYPE
			SYNTAX DisplayString
			MAX-ACCESS read-only
			STATUS current
			DESCRIPTION 
			"Issuer location of current certificate, with length of [0,64]." 
			::= { caCertInfoEntry 11 } 		
		
		caCertIssuerOrganization OBJECT-TYPE
			SYNTAX DisplayString
			MAX-ACCESS read-only
			STATUS current
			DESCRIPTION 
			"Issuer organization of current certificate, with length of [0,64]." 
			::= { caCertInfoEntry 12 }  
				
		caCertIssuerOrganizationUnit OBJECT-TYPE
			SYNTAX DisplayString
			MAX-ACCESS read-only
			STATUS current
			DESCRIPTION 
			"Issuer organization unit of current certificate, with length of [0,64]." 
			::= { caCertInfoEntry 13 }

		caCertIssuerCommonName OBJECT-TYPE
			SYNTAX DisplayString
			MAX-ACCESS read-only
			STATUS current
			DESCRIPTION 
			"Issuer common name of current certificate, with length of [1,64]." 
			::= { caCertInfoEntry 14 }  
		
		
		caCertStartTime OBJECT-TYPE
			SYNTAX DisplayString
			MAX-ACCESS read-only
			STATUS current
			DESCRIPTION 
			"Start time of current certificate." 
			::= { caCertInfoEntry 15 }
				
		caCertExpiration OBJECT-TYPE
			SYNTAX DisplayString
			MAX-ACCESS read-only
			STATUS current
			DESCRIPTION 
			"Expiration of current certificate." 
			::= { caCertInfoEntry 16 }
				
		caCertSN OBJECT-TYPE
			SYNTAX DisplayString
			MAX-ACCESS read-only
			STATUS current
			DESCRIPTION 
			"Serial Number of current certificate." 
			::= { caCertInfoEntry 17 }
			
	hwTrap OBJECT IDENTIFIER ::= { hwiBMC 500 } 
	
	hwTrapVar OBJECT IDENTIFIER ::= { hwTrap 1 }

		hwTrapSeq OBJECT-TYPE
			SYNTAX INTEGER
			MAX-ACCESS read-only
			STATUS current
			DESCRIPTION
				"Trap sequence"
			::= { hwTrapVar 1 }
			
		hwTrapSensorName OBJECT-TYPE
			SYNTAX DisplayString
			MAX-ACCESS read-only
			STATUS current
			DESCRIPTION
				"Trap sensor name"
			::= { hwTrapVar 2 }   
			
		hwTrapEvent OBJECT-TYPE
			SYNTAX DisplayString
			MAX-ACCESS read-only
			STATUS current
			DESCRIPTION
				"Trap description "
			::= { hwTrapVar 3 }
			
		hwTrapSeverity OBJECT-TYPE
			SYNTAX INTEGER
			        {
				ok(1),
				minor(2),
				major(3),
				critical(4)
				}
			MAX-ACCESS read-only
			STATUS current
			DESCRIPTION
				"Trap severity
				1  - ok,
				2  - minor,
				3  - major,
				4  - critical."
			::= { hwTrapVar 4 }
			
		hwTrapEventCode OBJECT-TYPE
			SYNTAX DisplayString
			MAX-ACCESS read-only
			STATUS current
			DESCRIPTION
				"Trap EventCode"
			::= { hwTrapVar 5 } 
			
		hwTrapEventData2 OBJECT-TYPE
			SYNTAX INTEGER
			MAX-ACCESS read-only
			STATUS current
			DESCRIPTION
				"Trap Event Data 2"
			::= { hwTrapVar 6 }
			
		hwTrapEventData3 OBJECT-TYPE
			SYNTAX INTEGER
			MAX-ACCESS read-only
			STATUS current
			DESCRIPTION
				"Trap Event Data 3"
			::= { hwTrapVar 7 } 
			
		hwTrapServerIdentity OBJECT-TYPE
			SYNTAX DisplayString
			MAX-ACCESS read-only
			STATUS current
			DESCRIPTION
				"Trap Sever Identity"
			::= { hwTrapVar 8 }
			
		hwTrapLocation OBJECT-TYPE
			SYNTAX DisplayString
			MAX-ACCESS read-only
			STATUS current
			DESCRIPTION
				"Trap location"
			::= { hwTrapVar 9 }

		hwTrapTime OBJECT-TYPE
			SYNTAX DisplayString
			MAX-ACCESS read-only
			STATUS current
			DESCRIPTION
				"Trap time"
			::= { hwTrapVar 10 }
--		****** hwServerTRAPObject Begin ******	
	hwServerTRAPObject OBJECT IDENTIFIER ::= { hwTrap 10 }
	hwOEM OBJECT IDENTIFIER ::= {hwServerTRAPObject 1}     
		hwOEMEvent NOTIFICATION-TYPE
			OBJECTS { hwTrapSeq, hwTrapEvent,hwTrapSeverity,hwTrapServerIdentity, hwTrapLocation, hwTrapTime } 
			STATUS  current
			DESCRIPTION
				"Huawei OEM event"
			::= { hwOEM 1 }

	hwPhysicalSecurity OBJECT IDENTIFIER ::= {hwServerTRAPObject 5} 
    
		hwChassisIntrusion NOTIFICATION-TYPE
			OBJECTS { hwTrapSeq, hwTrapSensorName, hwTrapEvent, hwTrapSeverity, hwTrapEventCode, hwTrapServerIdentity, hwTrapLocation, hwTrapTime } 
			STATUS  current
			DESCRIPTION
				"General Chassis Intrusion"
			::= { hwPhysicalSecurity 1 }
	  
		hwChassisIntrusionDeassert NOTIFICATION-TYPE
			OBJECTS { hwTrapSeq, hwTrapSensorName, hwTrapEvent, hwTrapSeverity, hwTrapEventCode, hwTrapServerIdentity, hwTrapLocation, hwTrapTime } 
			STATUS  current
			DESCRIPTION
				"General Chassis Intrusion Deassert"
			::= { hwPhysicalSecurity 2 }	  
	
	hwCPU OBJECT IDENTIFIER ::= {hwServerTRAPObject 7} 
    
		hwCPUCATError NOTIFICATION-TYPE
			OBJECTS { hwTrapSeq, hwTrapSensorName, hwTrapEvent, hwTrapSeverity, hwTrapEventCode, hwTrapServerIdentity, hwTrapLocation, hwTrapTime }
			STATUS  current
			DESCRIPTION
				"CPU CAT error"
			::= { hwCPU 1 }

		hwCPUCATErrorDeassert NOTIFICATION-TYPE
			OBJECTS { hwTrapSeq, hwTrapSensorName, hwTrapEvent, hwTrapSeverity, hwTrapEventCode, hwTrapServerIdentity, hwTrapLocation, hwTrapTime }
			STATUS  current
			DESCRIPTION
				"CPU CAT error deassert"
			::= { hwCPU 2 }

		hwCPUThermalTrip NOTIFICATION-TYPE
			OBJECTS { hwTrapSeq, hwTrapSensorName, hwTrapEvent, hwTrapSeverity, hwTrapEventCode, hwTrapServerIdentity, hwTrapLocation, hwTrapTime }
			STATUS  current
			DESCRIPTION
				"CPU thermal trip"
			::= { hwCPU 17 }

		hwCPUThermalTripDeassert NOTIFICATION-TYPE
			OBJECTS { hwTrapSeq, hwTrapSensorName, hwTrapEvent, hwTrapSeverity, hwTrapEventCode, hwTrapServerIdentity, hwTrapLocation, hwTrapTime }
			STATUS  current
			DESCRIPTION
				"CPU thermal trip deassert"
			::= { hwCPU 18 }

		hwCPUSelfTestFail NOTIFICATION-TYPE
			OBJECTS { hwTrapSeq, hwTrapSensorName, hwTrapEvent, hwTrapSeverity, hwTrapEventCode, hwTrapServerIdentity, hwTrapLocation, hwTrapTime }
			STATUS  current
			DESCRIPTION
				"CPU FRB1/BIST failure"
			::= { hwCPU 33 }

		hwCPUSelfTestFailDeassert NOTIFICATION-TYPE
			OBJECTS { hwTrapSeq, hwTrapSensorName, hwTrapEvent, hwTrapSeverity, hwTrapEventCode, hwTrapServerIdentity, hwTrapLocation, hwTrapTime }
			STATUS  current
			DESCRIPTION
				"CPU FRB1/BIST failure deassert"
			::= { hwCPU 34 }


		hwCPUCfgError NOTIFICATION-TYPE
			OBJECTS { hwTrapSeq, hwTrapSensorName, hwTrapEvent, hwTrapSeverity, hwTrapEventCode, hwTrapServerIdentity, hwTrapLocation, hwTrapTime }
			STATUS  current
			DESCRIPTION
				"CPU configure error"
			::= { hwCPU 81 }

		hwCPUCfgErrorDeassert NOTIFICATION-TYPE
			OBJECTS { hwTrapSeq, hwTrapSensorName, hwTrapEvent, hwTrapSeverity, hwTrapEventCode, hwTrapServerIdentity, hwTrapLocation, hwTrapTime }
			STATUS  current
			DESCRIPTION
				"CPU configure error deassert"
			::= { hwCPU 82 }

		hwCPUPresence NOTIFICATION-TYPE
			OBJECTS { hwTrapSeq, hwTrapSensorName, hwTrapEvent, hwTrapSeverity, hwTrapEventCode, hwTrapServerIdentity, hwTrapLocation, hwTrapTime }
			STATUS  current
			DESCRIPTION
				"CPU Presence"
			::= { hwCPU 113 }

		hwCPUPresenceDeassert NOTIFICATION-TYPE
			OBJECTS { hwTrapSeq, hwTrapSensorName, hwTrapEvent, hwTrapSeverity, hwTrapEventCode, hwTrapServerIdentity, hwTrapLocation, hwTrapTime }
			STATUS  current
			DESCRIPTION
				"CPU Presence deassert"
			::= { hwCPU 114 }

		hwCPUOffline NOTIFICATION-TYPE
			OBJECTS { hwTrapSeq, hwTrapSensorName, hwTrapEvent, hwTrapSeverity, hwTrapEventCode, hwTrapServerIdentity, hwTrapLocation, hwTrapTime }
			STATUS  current
			DESCRIPTION
				"CPU offline"
			::= { hwCPU 129 }

		hwCPUOfflineDeassert NOTIFICATION-TYPE
			OBJECTS { hwTrapSeq, hwTrapSensorName, hwTrapEvent, hwTrapSeverity, hwTrapEventCode, hwTrapServerIdentity, hwTrapLocation, hwTrapTime }
			STATUS  current
			DESCRIPTION
				"CPU offline deassert"
			::= { hwCPU 130 }

		hwCPUMCE NOTIFICATION-TYPE
			OBJECTS { hwTrapSeq, hwTrapSensorName, hwTrapEvent, hwTrapSeverity, hwTrapEventCode, hwTrapServerIdentity, hwTrapLocation, hwTrapTime }
			STATUS  current
			DESCRIPTION
				"CPU MCE occured"
			::= { hwCPU 177 }

		hwCPUMCEDeassert NOTIFICATION-TYPE
			OBJECTS { hwTrapSeq, hwTrapSensorName, hwTrapEvent, hwTrapSeverity, hwTrapEventCode, hwTrapServerIdentity, hwTrapLocation, hwTrapTime }
			STATUS  current
			DESCRIPTION
				"CPU MCE deassert"
			::= { hwCPU 178 }  

		hwVMSELinkFail NOTIFICATION-TYPE
			OBJECTS { hwTrapSeq, hwTrapSensorName, hwTrapEvent, hwTrapSeverity, hwTrapEventCode, hwTrapServerIdentity, hwTrapLocation, hwTrapTime }
			STATUS  current
			DESCRIPTION
				"CPU VMSE link failure in mirror mode"
			::= { hwCPU 193 }

		hwVMSELinkFailDeassert NOTIFICATION-TYPE
			OBJECTS { hwTrapSeq, hwTrapSensorName, hwTrapEvent, hwTrapSeverity, hwTrapEventCode, hwTrapServerIdentity, hwTrapLocation, hwTrapTime }
			STATUS  current
			DESCRIPTION
				"CPU VMSE link failure in mirror mode deassert"
			::= { hwCPU 194 }

	
	hwPowerSupply OBJECT IDENTIFIER ::= {hwServerTRAPObject 8}
    
		hwPowerSupplyFault NOTIFICATION-TYPE
			OBJECTS { hwTrapSeq, hwTrapSensorName, hwTrapEvent, hwTrapSeverity, hwTrapEventCode, hwTrapServerIdentity, hwTrapLocation, hwTrapTime }
			STATUS  current
			DESCRIPTION
				"Power Supply Fault"
			::= { hwPowerSupply 17 }

		hwPowerSupplyFaultDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Power Supply Fault Deassert"
			::= { hwPowerSupply 18 }


		hwPowerSupplyPredictiveFailure NOTIFICATION-TYPE
			OBJECTS { hwTrapSeq, hwTrapSensorName, hwTrapEvent, hwTrapSeverity, hwTrapEventCode, hwTrapServerIdentity, hwTrapLocation, hwTrapTime }
			STATUS  current
			DESCRIPTION
				"Power Supply Predictive Failure"
			::= { hwPowerSupply 33 }

		hwPowerSupplyPredictiveFailureDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Power Supply Predictive Failure Deassert"
			::= { hwPowerSupply 34 }

		hwPowerSupplyInputLost NOTIFICATION-TYPE
			OBJECTS { hwTrapSeq, hwTrapSensorName, hwTrapEvent, hwTrapSeverity, hwTrapEventCode, hwTrapServerIdentity, hwTrapLocation, hwTrapTime }
			STATUS  current
			DESCRIPTION
				"Power Supply input lost"
			::= { hwPowerSupply 49 }

		hwPowerSupplyInputLostDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Power Supply input lost Deassert"
			::= { hwPowerSupply 50 }
	  
		hwPowerSupplyACLost NOTIFICATION-TYPE
			OBJECTS { hwTrapSeq, hwTrapSensorName, hwTrapEvent, hwTrapSeverity, hwTrapEventCode, hwTrapServerIdentity, hwTrapLocation, hwTrapTime }
			STATUS  current
			DESCRIPTION
				"AC lost or out-of-range"
			::= { hwPowerSupply 65 }
	  
		hwPowerSupplyACLostDeassert NOTIFICATION-TYPE
			OBJECTS { hwTrapSeq, hwTrapSensorName, hwTrapEvent, hwTrapSeverity, hwTrapEventCode, hwTrapServerIdentity, hwTrapLocation, hwTrapTime }
			STATUS  current
			DESCRIPTION
				"AC lost or out-of-range Deassert"
			::= { hwPowerSupply 66 }

		hwPowerSupplyOvertemp NOTIFICATION-TYPE
			OBJECTS { hwTrapSeq, hwTrapSensorName, hwTrapEvent, hwTrapSeverity, hwTrapEventCode, hwTrapServerIdentity, hwTrapLocation, hwTrapTime }
			STATUS  current
			DESCRIPTION
				"PSU overheating. (Generated)"
			::= { hwPowerSupply 81 }

		hwPowerSupplyOvertempDeassert NOTIFICATION-TYPE
			OBJECTS { hwTrapSeq, hwTrapSensorName, hwTrapEvent, hwTrapSeverity, hwTrapEventCode, hwTrapServerIdentity, hwTrapLocation, hwTrapTime }
			STATUS  current
			DESCRIPTION
				"PSU overheating. (Cleared)"
			::= { hwPowerSupply 82 }
	hwMemory OBJECT IDENTIFIER ::= {hwServerTRAPObject 12}
    
		hwCorrectableECC NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory correctable ECC error occurred"
			::= { hwMemory 1 }

		hwCorrectableECCDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory correctable ECC error deassert"
			::= { hwMemory 2 }

		hwUncorrectableECC NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory uncorrectable ECC error occurred"
			::= { hwMemory 17 }

		hwUncorrectableECCDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory uncorrectable ECC error deassert"
			::= { hwMemory 18 }

		hwMemoryECCLimitation NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory correctable ECC logging limit reached detected"
			::= { hwMemory 81 }

		hwMemoryECCLimitationDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory correctable ECC logging limit reached deassert"
			::= { hwMemory 82 }


		hwMemoryPresence NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory presence detected"
			::= { hwMemory 97 }

		hwMemoryPresenceDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory presence deassert"
			::= { hwMemory 98 }


		hwMemoryCfgError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory config error detected"
			::= { hwMemory 113 }

		hwMemoryCfgErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory config error deassert"
			::= { hwMemory 114 }

		hwMemorySpare NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory spare detected"
			::= { hwMemory 129 }

		hwMemorySpareDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory spare deassert"
			::= { hwMemory 130 }

		hwMemoryOvertemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory overtemperature detected"
			::= { hwMemory 161 }

		hwMemoryOvertempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"memory overtemperature deassert"
			::= { hwMemory 162 }

	
	hwStorageDevice OBJECT IDENTIFIER ::= {hwServerTRAPObject 13}
    
		hwStorageDevicePresence NOTIFICATION-TYPE
			OBJECTS { hwTrapSeq, hwTrapSensorName, hwTrapEvent, hwTrapSeverity, hwTrapEventCode, hwTrapServerIdentity, hwTrapLocation, hwTrapTime }
			STATUS  current
			DESCRIPTION
				"Storage device presence detected"
			::= { hwStorageDevice 1 }

		hwStorageDevicePresenceDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Storage device presence deassert"
			::= { hwStorageDevice 2 }

		hwStorageDeviceFault NOTIFICATION-TYPE
			OBJECTS { hwTrapSeq, hwTrapSensorName, hwTrapEvent, hwTrapSeverity, hwTrapEventCode, hwTrapServerIdentity, hwTrapLocation, hwTrapTime }
			STATUS  current
			DESCRIPTION
				"Storage device fault detected"
			::= { hwStorageDevice 17 }

		hwStorageDeviceFaultDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Storage device fault deassert"
			::= { hwStorageDevice 18 }

		hwStorageDevicePredictiveFailure NOTIFICATION-TYPE
			OBJECTS { hwTrapSeq, hwTrapSensorName, hwTrapEvent, hwTrapSeverity, hwTrapEventCode, hwTrapServerIdentity, hwTrapLocation, hwTrapTime }
			STATUS  current
			DESCRIPTION
				"Storage device predictive failure"
			::= { hwStorageDevice 33 }

		hwStorageDevicePredictiveFailureDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Storage device predictive failure deassert"
			::= { hwStorageDevice 34 }
	  
		hwRAIDArrayFail NOTIFICATION-TYPE
			OBJECTS { hwTrapSeq, hwTrapSensorName, hwTrapEvent, hwTrapSeverity, hwTrapEventCode, hwTrapServerIdentity, hwTrapLocation, hwTrapTime }
			STATUS  current
			DESCRIPTION
				"RAID array fail detected"
			::= { hwStorageDevice 97 }

		hwRAIDArrayFailDeassert NOTIFICATION-TYPE
			OBJECTS { hwTrapSeq, hwTrapSensorName, hwTrapEvent, hwTrapSeverity, hwTrapEventCode, hwTrapServerIdentity, hwTrapLocation, hwTrapTime }
			STATUS  current
			DESCRIPTION
				"RAID array fail deassert"
			::= { hwStorageDevice 98 }

		hwRAIDRebuild NOTIFICATION-TYPE
			OBJECTS { hwTrapSeq, hwTrapSensorName, hwTrapEvent, hwTrapSeverity, hwTrapEventCode, hwTrapServerIdentity, hwTrapLocation, hwTrapTime }
			STATUS  current
			DESCRIPTION
				"RAID rebuild detected"
			::= { hwStorageDevice 113 }

		hwRAIDRebuildDeassert NOTIFICATION-TYPE
			OBJECTS { hwTrapSeq, hwTrapSensorName, hwTrapEvent, hwTrapSeverity, hwTrapEventCode, hwTrapServerIdentity, hwTrapLocation, hwTrapTime }
			STATUS  current
			DESCRIPTION
				"RAID rebuild deassert"
			::= { hwStorageDevice 114 }
	  
		hwRAIDRebuildAborted NOTIFICATION-TYPE
			OBJECTS { hwTrapSeq, hwTrapSensorName, hwTrapEvent, hwTrapSeverity, hwTrapEventCode, hwTrapServerIdentity, hwTrapLocation, hwTrapTime }
			STATUS  current
			DESCRIPTION
				"RAID rebuild aborted detected"
			::= { hwStorageDevice 129 }
	  
		hwRAIDRebuildAbortedDeassert NOTIFICATION-TYPE
			OBJECTS { hwTrapSeq, hwTrapSensorName, hwTrapEvent, hwTrapSeverity, hwTrapEventCode, hwTrapServerIdentity, hwTrapLocation, hwTrapTime }
			STATUS  current
			DESCRIPTION
				"RAID rebuild aborted deassert"
			::= { hwStorageDevice 130 }
 	
	hwSysFWProgress OBJECT IDENTIFIER ::= {hwServerTRAPObject 15} 
    
		hwSystemFirmwareHang NOTIFICATION-TYPE
			OBJECTS { hwTrapSeq, hwTrapSensorName, hwTrapEvent, hwTrapSeverity, hwTrapEventCode, hwTrapServerIdentity, hwTrapLocation, hwTrapTime }
			STATUS  current
			DESCRIPTION
				"System firmware hang"
			::= { hwSysFWProgress 17 }

		hwSystemFirmwareHangDeassert NOTIFICATION-TYPE
			OBJECTS { hwTrapSeq, hwTrapSensorName, hwTrapEvent, hwTrapSeverity, hwTrapEventCode, hwTrapServerIdentity, hwTrapLocation, hwTrapTime }
			STATUS  current
			DESCRIPTION
				"System firmware hang deassert"
			::= { hwSysFWProgress 18 }
    
		hwPS2USBFault NOTIFICATION-TYPE
			OBJECTS { hwTrapSeq, hwTrapSensorName, hwTrapEvent, hwTrapSeverity, hwTrapEventCode, hwTrapServerIdentity, hwTrapLocation, hwTrapTime }
			STATUS  current
			DESCRIPTION
				"Unrecoverable PS/2 or USB keyboard failure"
			::= { hwSysFWProgress 1793 }

		hwPS2USBFaultDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Unrecoverable PS/2 or USB keyboard failure deassert"
			::= { hwSysFWProgress 1794 }

		hwVideoControllerFault NOTIFICATION-TYPE
			OBJECTS { hwTrapSeq, hwTrapSensorName, hwTrapEvent, hwTrapSeverity, hwTrapEventCode, hwTrapServerIdentity, hwTrapLocation, hwTrapTime }
			STATUS  current
			DESCRIPTION
				"Unrecoverable video controller failure"
			::= { hwSysFWProgress 2305 }

		hwVideoControllerFaultDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Unrecoverable video controller failure deassert"
			::= { hwSysFWProgress 2306 }

		hwCPUVoltageMismatch NOTIFICATION-TYPE
			OBJECTS { hwTrapSeq, hwTrapSensorName, hwTrapEvent, hwTrapSeverity, hwTrapEventCode, hwTrapServerIdentity, hwTrapLocation, hwTrapTime }
			STATUS  current
			DESCRIPTION
				"CPU voltage mismatch"
			::= { hwSysFWProgress 3073 }

		hwCPUVoltageMismatchDeassert NOTIFICATION-TYPE
			OBJECTS { hwTrapSeq, hwTrapSensorName, hwTrapEvent, hwTrapSeverity, hwTrapEventCode, hwTrapServerIdentity, hwTrapLocation, hwTrapTime }
			STATUS  current
			DESCRIPTION
				"CPU voltage mismatch deassert"
			::= { hwSysFWProgress 3074 }

		hwSystemNoMemory NOTIFICATION-TYPE
			OBJECTS { hwTrapSeq, hwTrapSensorName, hwTrapEvent, hwTrapSeverity, hwTrapEventCode, hwTrapServerIdentity, hwTrapLocation, hwTrapTime }
			STATUS  current
			DESCRIPTION
				"System no memory detected"
			::= { hwSysFWProgress 257 }

		hwSystemNoMemoryDeassert NOTIFICATION-TYPE
			OBJECTS { hwTrapSeq, hwTrapSensorName, hwTrapEvent, hwTrapSeverity, hwTrapEventCode, hwTrapServerIdentity, hwTrapLocation, hwTrapTime }
			STATUS  current
			DESCRIPTION
				"System no memory detected deassert"
			::= { hwSysFWProgress 258 }
      

 	
	hwSysEvent OBJECT IDENTIFIER ::= {hwServerTRAPObject 18} 
    
		hwSysEventInstance NOTIFICATION-TYPE
			OBJECTS { hwTrapSeq, hwTrapSensorName, hwTrapEvent, hwTrapSeverity, hwTrapEventCode, hwTrapServerIdentity, hwTrapLocation, hwTrapTime }
			STATUS  current
			DESCRIPTION
				"PEF action"
			::= { hwSysEvent 65 }

		hwSystemError NOTIFICATION-TYPE
			OBJECTS { hwTrapSeq, hwTrapSensorName, hwTrapEvent, hwTrapSeverity, hwTrapEventCode, hwTrapServerIdentity, hwTrapLocation, hwTrapTime }
			STATUS  current
			DESCRIPTION
				"System hang up/reset. For more information, see the background log"
			::= { hwSysEvent 33 }

		hwSystemErrorDeassert NOTIFICATION-TYPE
			OBJECTS { hwTrapSeq, hwTrapSensorName, hwTrapEvent, hwTrapSeverity, hwTrapEventCode, hwTrapServerIdentity, hwTrapLocation, hwTrapTime }
			STATUS  current
			DESCRIPTION
				"System hang up/reset deassert"
			::= { hwSysEvent 34 }
 	
	hwButton OBJECT IDENTIFIER ::= {hwServerTRAPObject 20}                         

		hwPowerButtonPressed NOTIFICATION-TYPE
			OBJECTS { hwTrapSeq, hwTrapSensorName, hwTrapEvent, hwTrapSeverity, hwTrapEventCode, hwTrapServerIdentity, hwTrapLocation, hwTrapTime }
			STATUS  current
			DESCRIPTION
				"Power button pressed"
			::= { hwButton 1 }

		hwPCIeHotSwapButtonPressed NOTIFICATION-TYPE
			OBJECTS { hwTrapSeq, hwTrapSensorName, hwTrapEvent, hwTrapSeverity, hwTrapEventCode, hwTrapServerIdentity, hwTrapLocation, hwTrapTime }
			STATUS  current
			DESCRIPTION
				"PCIe card hot-swap button pressed"
			::= { hwButton 65 }

	
	hwCable OBJECT IDENTIFIER ::= {hwServerTRAPObject 27}
    
		hwCableStatus NOTIFICATION-TYPE
			OBJECTS { hwTrapSeq, hwTrapSensorName, hwTrapEvent, hwTrapSeverity, hwTrapEventCode, hwTrapServerIdentity, hwTrapLocation, hwTrapTime }
			STATUS  current
			DESCRIPTION
				"SAS or Harddisk backplane cable config error"
			::= { hwCable 17 }

		hwCableStatusDeassert NOTIFICATION-TYPE
			OBJECTS { hwTrapSeq, hwTrapSensorName, hwTrapEvent, hwTrapSeverity, hwTrapEventCode, hwTrapServerIdentity, hwTrapLocation, hwTrapTime }
			STATUS  current
			DESCRIPTION
				"SAS or Harddisk backplane cable config error deassert"
			::= { hwCable 18 }


	
	hwSysRestart OBJECT IDENTIFIER ::= {hwServerTRAPObject 29}
    
		hwSysRestartUnknown NOTIFICATION-TYPE
			OBJECTS { hwTrapSeq, hwTrapSensorName, hwTrapEvent, hwTrapSeverity, hwTrapEventCode, hwTrapServerIdentity, hwTrapLocation, hwTrapTime }
			STATUS  current
			DESCRIPTION
				"system restart cause unknown"
			::= { hwSysRestart 113 }

		hwSysRestartChassisCtrl NOTIFICATION-TYPE
			OBJECTS { hwTrapSeq, hwTrapSensorName, hwTrapEvent, hwTrapSeverity, hwTrapEventCode, hwTrapServerIdentity, hwTrapLocation, hwTrapTime }
			STATUS  current
			DESCRIPTION
				"system restart cause chassis control"
			::= { hwSysRestart 369 }

		hwSysRestartPowerButton NOTIFICATION-TYPE
			OBJECTS { hwTrapSeq, hwTrapSensorName, hwTrapEvent, hwTrapSeverity, hwTrapEventCode, hwTrapServerIdentity, hwTrapLocation, hwTrapTime }
			STATUS  current
			DESCRIPTION
				"system restart cause power button pressed"
			::= { hwSysRestart 881 }


		hwSysRestartWatchdogCtrl NOTIFICATION-TYPE
			OBJECTS { hwTrapSeq, hwTrapSensorName, hwTrapEvent, hwTrapSeverity, hwTrapEventCode, hwTrapServerIdentity, hwTrapLocation, hwTrapTime }
			STATUS  current
			DESCRIPTION
				"system restart cause Watchdog control"
			::= { hwSysRestart 1137 }
			
		hwSysRestartBMCCtrl NOTIFICATION-TYPE
			OBJECTS { hwTrapSeq, hwTrapSensorName, hwTrapEvent, hwTrapSeverity, hwTrapEventCode, hwTrapServerIdentity, hwTrapLocation, hwTrapTime }
			STATUS  current
			DESCRIPTION
				"system restart cause BMC control"
			::= { hwSysRestart 1393 }
      
		hwSysRestartAlwaysRestore NOTIFICATION-TYPE
			OBJECTS { hwTrapSeq, hwTrapSensorName, hwTrapEvent, hwTrapSeverity, hwTrapEventCode, hwTrapServerIdentity, hwTrapLocation, hwTrapTime }
			STATUS  current
			DESCRIPTION
				"system restart cause always power up"
			::= { hwSysRestart 1649 }

		hwSysRestartRestorePrevState NOTIFICATION-TYPE
			OBJECTS { hwTrapSeq, hwTrapSensorName, hwTrapEvent, hwTrapSeverity, hwTrapEventCode, hwTrapServerIdentity, hwTrapLocation, hwTrapTime }
			STATUS  current
			DESCRIPTION
				"system restart cause always restore previous state"
			::= { hwSysRestart 1905 }
	
	hwBootError OBJECT IDENTIFIER ::= {hwServerTRAPObject 30}
    
		hwNoBootableMedia NOTIFICATION-TYPE
			OBJECTS { hwTrapSeq, hwTrapSensorName, hwTrapEvent, hwTrapSeverity, hwTrapEventCode, hwTrapServerIdentity, hwTrapLocation, hwTrapTime }
			STATUS  current
			DESCRIPTION
				"boot error, no bootable media"
			::= { hwBootError 1 }

		hwNoBootableMediaDeassert NOTIFICATION-TYPE
			OBJECTS { hwTrapSeq, hwTrapSensorName, hwTrapEvent, hwTrapSeverity, hwTrapEventCode, hwTrapServerIdentity, hwTrapLocation, hwTrapTime }
			STATUS  current
			DESCRIPTION
				"boot error, no bootable media deassert"
			::= { hwBootError 2 }

		hwNoBootableDisk NOTIFICATION-TYPE
			OBJECTS { hwTrapSeq, hwTrapSensorName, hwTrapEvent, hwTrapSeverity, hwTrapEventCode, hwTrapServerIdentity, hwTrapLocation, hwTrapTime }
			STATUS  current
			DESCRIPTION
				"boot error, Non-bootable disk in drive"
			::= { hwBootError 17 }

		hwNoBootableDiskDeassert NOTIFICATION-TYPE
			OBJECTS { hwTrapSeq, hwTrapSensorName, hwTrapEvent, hwTrapSeverity, hwTrapEventCode, hwTrapServerIdentity, hwTrapLocation, hwTrapTime }
			STATUS  current
			DESCRIPTION
				"boot error, Non-bootable disk in drive deassert"
			::= { hwBootError 18 }

		hwPXENotFound NOTIFICATION-TYPE
			OBJECTS { hwTrapSeq, hwTrapSensorName, hwTrapEvent, hwTrapSeverity, hwTrapEventCode, hwTrapServerIdentity, hwTrapLocation, hwTrapTime }
			STATUS  current
			DESCRIPTION
				"boot error, PXE server not found"
			::= { hwBootError 33 }

		hwPXENotFoundDeassert NOTIFICATION-TYPE
			OBJECTS { hwTrapSeq, hwTrapSensorName, hwTrapEvent, hwTrapSeverity, hwTrapEventCode, hwTrapServerIdentity, hwTrapLocation, hwTrapTime }
			STATUS  current
			DESCRIPTION
				"boot error, PXE server not found deassert"
			::= { hwBootError 34 }


		hwInvalidBootSector NOTIFICATION-TYPE
			OBJECTS { hwTrapSeq, hwTrapSensorName, hwTrapEvent, hwTrapSeverity, hwTrapEventCode, hwTrapServerIdentity, hwTrapLocation, hwTrapTime }
			STATUS  current
			DESCRIPTION
				"boot error, Invalid boot sector"
			::= { hwBootError 49 }

		hwInvalidBootSectorDeassert NOTIFICATION-TYPE
			OBJECTS { hwTrapSeq, hwTrapSensorName, hwTrapEvent, hwTrapSeverity, hwTrapEventCode, hwTrapServerIdentity, hwTrapLocation, hwTrapTime }
			STATUS  current
			DESCRIPTION
				"boot error, Invalid boot sector deassert"
			::= { hwBootError 50 }

	
 	
	hwDeviceFault OBJECT IDENTIFIER ::= {hwServerTRAPObject 33}
    
    
		hwHardwareAddrFault NOTIFICATION-TYPE
			OBJECTS { hwTrapSeq, hwTrapSensorName, hwTrapEvent, hwTrapSeverity, hwTrapEventCode, hwTrapServerIdentity, hwTrapLocation, hwTrapTime }
			STATUS  current
			DESCRIPTION
				"Hardware address in fault status"
			::= { hwDeviceFault 1 }


		hwHardwareAddrFaultDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Hardware address in fault status deassert"
			::= { hwDeviceFault 2 }

		hwLossBmaHeartBeat NOTIFICATION-TYPE
			OBJECTS { hwTrapSeq, hwTrapSensorName, hwTrapEvent, hwTrapSeverity, hwTrapEventCode, hwTrapServerIdentity, hwTrapLocation, hwTrapTime }
			STATUS  current
			DESCRIPTION
				"Heartbeat signals between the iBMC and iBMA are lost"
			::= { hwDeviceFault 17 }


		hwLossBmaHeartBeatDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Heartbeat signals between the iBMC and iBMA are normal"
			::= { hwDeviceFault 18 }
	  
		hwDeviceInstall NOTIFICATION-TYPE
			OBJECTS { hwTrapSeq, hwTrapSensorName, hwTrapEvent, hwTrapSeverity, hwTrapEventCode, hwTrapServerIdentity, hwTrapLocation, hwTrapTime }
			STATUS  current
			DESCRIPTION
				"Device installed"
			::= { hwDeviceFault 33 }


		hwDeviceInstallDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Device installed deassert"
			::= { hwDeviceFault 34 }   
     
		hwEthLinkDown NOTIFICATION-TYPE
			OBJECTS { hwTrapSeq, hwTrapSensorName, hwTrapEvent, hwTrapSeverity, hwTrapEventCode, hwTrapServerIdentity, hwTrapLocation, hwTrapTime }
			STATUS  current
			DESCRIPTION
				"System Eth link down"
			::= { hwDeviceFault 129 }


		hwEthLinkDownDeassert NOTIFICATION-TYPE
			OBJECTS { hwTrapSeq, hwTrapSensorName, hwTrapEvent, hwTrapSeverity, hwTrapEventCode, hwTrapServerIdentity, hwTrapLocation, hwTrapTime }
			STATUS  current
			DESCRIPTION
				"System Eth link down deassert"
			::= { hwDeviceFault 130 } 
      
      
		hwMemBrdMigrate NOTIFICATION-TYPE
			OBJECTS { hwTrapSeq, hwTrapSensorName, hwTrapEvent, hwTrapSeverity, hwTrapEventCode, hwTrapServerIdentity, hwTrapLocation, hwTrapTime }
			STATUS  current
			DESCRIPTION
				"Spare Device"
			::= { hwDeviceFault 145 } 
	  
		hwMemBrdMigrateDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Spare Device deassert"
			::= { hwDeviceFault 146 } 
	  
		hwPCIEStatus NOTIFICATION-TYPE
			OBJECTS { hwTrapSeq, hwTrapSensorName, hwTrapEvent, hwTrapSeverity, hwTrapEventCode, hwTrapServerIdentity, hwTrapLocation, hwTrapTime }
			STATUS  current
			DESCRIPTION
				"PCIe Error"
			::= { hwDeviceFault 257 } 
	  
		hwPCIEStatusDeassert NOTIFICATION-TYPE
			OBJECTS { hwTrapSeq, hwTrapSensorName, hwTrapEvent, hwTrapSeverity, hwTrapEventCode, hwTrapServerIdentity, hwTrapLocation, hwTrapTime }
			STATUS  current
			DESCRIPTION
				"PCIe Error deassert"
			::= { hwDeviceFault 258 } 
      
		hwFanFault NOTIFICATION-TYPE
			OBJECTS { hwTrapSeq, hwTrapSensorName, hwTrapEvent, hwTrapSeverity, hwTrapEventCode, hwTrapServerIdentity, hwTrapLocation, hwTrapTime }
			STATUS  current
			DESCRIPTION
				"fan in fault status"
			::= { hwDeviceFault 2049 }

		hwFanFaultDeassert NOTIFICATION-TYPE
			OBJECTS { hwTrapSeq, hwTrapSensorName, hwTrapEvent, hwTrapSeverity, hwTrapEventCode, hwTrapServerIdentity, hwTrapLocation, hwTrapTime }
			STATUS  current
			DESCRIPTION
				"fan in fault status deassert"
			::= { hwDeviceFault 2050 }

		hwPCIeFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"PCIe in fault status"
			::= { hwDeviceFault 2305 }

		hwPCIeFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS  current
			DESCRIPTION
				"PCIe in fault status deassert"
			::= { hwDeviceFault 2306 } 



	
	hwACPIStatus OBJECT IDENTIFIER ::= {hwServerTRAPObject 34}                         
    
		hwACPIStatusS0 NOTIFICATION-TYPE
			OBJECTS { hwTrapSeq, hwTrapSensorName, hwTrapEvent, hwTrapSeverity, hwTrapEventCode, hwTrapServerIdentity, hwTrapLocation, hwTrapTime }
			STATUS  current
			DESCRIPTION
				"ACPI status S0"
			::= { hwACPIStatus 1 }

		hwACPIStatusS4S5 NOTIFICATION-TYPE
			OBJECTS { hwTrapSeq, hwTrapSensorName, hwTrapEvent, hwTrapSeverity, hwTrapEventCode, hwTrapServerIdentity, hwTrapLocation, hwTrapTime }
			STATUS  current
			DESCRIPTION
				"ACPI status, S4/S5 soft-off, particular when S4/S5 state cannot be determined"
			::= { hwACPIStatus 97 }

	
	hwWatchDog OBJECT IDENTIFIER ::= {hwServerTRAPObject 35}
    
		hwWatchDogOverflow NOTIFICATION-TYPE
			OBJECTS { hwTrapSeq, hwTrapSensorName, hwTrapEvent, hwTrapSeverity, hwTrapEventCode, hwTrapServerIdentity, hwTrapLocation, hwTrapTime }
			STATUS  current
			DESCRIPTION
				"watchdog overflow, no action"
			::= { hwWatchDog 1 }

		hwWatchDogOverflowDeassert NOTIFICATION-TYPE
			OBJECTS { hwTrapSeq, hwTrapSensorName, hwTrapEvent, hwTrapSeverity, hwTrapEventCode, hwTrapServerIdentity, hwTrapLocation, hwTrapTime }
			STATUS  current
			DESCRIPTION
				"watchdog overflow, no action deassert"
			::= { hwWatchDog 2 }
      
		hwWatchDogReset NOTIFICATION-TYPE
			OBJECTS { hwTrapSeq, hwTrapSensorName, hwTrapEvent, hwTrapSeverity, hwTrapEventCode, hwTrapServerIdentity, hwTrapLocation, hwTrapTime }
			STATUS  current
			DESCRIPTION
				"watchdog overflow, hard reset"
			::= { hwWatchDog 17 }

		hwWatchDogResetDeassert NOTIFICATION-TYPE
			OBJECTS { hwTrapSeq, hwTrapSensorName, hwTrapEvent, hwTrapSeverity, hwTrapEventCode, hwTrapServerIdentity, hwTrapLocation, hwTrapTime }
			STATUS  current
			DESCRIPTION
				"watchdog overflow, hard reset deassert"
			::= { hwWatchDog 18 }

		hwWatchDogPowerDown NOTIFICATION-TYPE
			OBJECTS { hwTrapSeq, hwTrapSensorName, hwTrapEvent, hwTrapSeverity, hwTrapEventCode, hwTrapServerIdentity, hwTrapLocation, hwTrapTime }
			STATUS  current
			DESCRIPTION
				"watchdog overflow, power down"
			::= { hwWatchDog 33 }

		hwWatchDogPowerDownDeassert NOTIFICATION-TYPE
			OBJECTS { hwTrapSeq, hwTrapSensorName, hwTrapEvent, hwTrapSeverity, hwTrapEventCode, hwTrapServerIdentity, hwTrapLocation, hwTrapTime }
			STATUS  current
			DESCRIPTION
				"watchdog overflow, power down deassert"
			::= { hwWatchDog 34 }

		hwWatchDogPowerCycle NOTIFICATION-TYPE
			OBJECTS { hwTrapSeq, hwTrapSensorName, hwTrapEvent, hwTrapSeverity, hwTrapEventCode, hwTrapServerIdentity, hwTrapLocation, hwTrapTime }
			STATUS  current
			DESCRIPTION
				"watchdog overflow, power cycle"
			::= { hwWatchDog 49 }

		hwWatchDogPowerCycleDeassert NOTIFICATION-TYPE
			OBJECTS { hwTrapSeq, hwTrapSensorName, hwTrapEvent, hwTrapSeverity, hwTrapEventCode, hwTrapServerIdentity, hwTrapLocation, hwTrapTime }
			STATUS  current
			DESCRIPTION
				"watchdog overflow, power cycle deassert"
			::= { hwWatchDog 50 }

	
	hwLANHeartBeat OBJECT IDENTIFIER ::= {hwServerTRAPObject 39}
    
		hwLANHeartLost NOTIFICATION-TYPE
			OBJECTS { hwTrapSeq, hwTrapSensorName, hwTrapEvent, hwTrapSeverity, hwTrapEventCode, hwTrapServerIdentity, hwTrapLocation, hwTrapTime }
			STATUS  current
			DESCRIPTION
				"LAN heart beat lost"
			::= { hwLANHeartBeat 1 }

		hwLANHeartLostDeassert NOTIFICATION-TYPE
			OBJECTS { hwTrapSeq, hwTrapSensorName, hwTrapEvent, hwTrapSeverity, hwTrapEventCode, hwTrapServerIdentity, hwTrapLocation, hwTrapTime }
			STATUS  current
			DESCRIPTION
				"LAN heart beat lost deassert"
			::= { hwLANHeartBeat 2 }

	
	hwMngmntHealth OBJECT IDENTIFIER ::= {hwServerTRAPObject 40}
    
		hwSensorAccessibleFail NOTIFICATION-TYPE
			OBJECTS { hwTrapSeq, hwTrapSensorName, hwTrapEvent, hwTrapSeverity, hwTrapEventCode, hwTrapServerIdentity, hwTrapLocation, hwTrapTime }
			STATUS  current
			DESCRIPTION
				"Sensor access degraded or unavailable"
			::= { hwMngmntHealth 1 } 

		hwSensorAccessibleFailDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Sensor access degraded or unavailable deassert"
			::= { hwMngmntHealth 2 }

		hwControllerAccessibleFail NOTIFICATION-TYPE
			OBJECTS { hwTrapSeq, hwTrapSensorName, hwTrapEvent, hwTrapSeverity, hwTrapEventCode, hwTrapServerIdentity, hwTrapLocation, hwTrapTime }
			STATUS  current
			DESCRIPTION
				"Controller access degraded or unavailable"
			::= { hwMngmntHealth 17 } 

		hwControllerAccessibleFailDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Controller access degraded or unavailable deassert"
			::= { hwMngmntHealth 18 }
			
		hwControllerUnavailableFail NOTIFICATION-TYPE
			OBJECTS { hwTrapSeq, hwTrapSensorName, hwTrapEvent, hwTrapSeverity, hwTrapEventCode, hwTrapServerIdentity, hwTrapLocation, hwTrapTime }
			STATUS  current
			DESCRIPTION
				"Management controller unavailable"
			::= { hwMngmntHealth 49 } 

		hwControllerUnavailableFailDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Management controller unavailable deassert"
			::= { hwMngmntHealth 50 }

		hwFruFail NOTIFICATION-TYPE
			OBJECTS { hwTrapSeq, hwTrapSensorName, hwTrapEvent, hwTrapSeverity, hwTrapEventCode, hwTrapServerIdentity, hwTrapLocation, hwTrapTime }
			STATUS  current
			DESCRIPTION
				"FRU failure"
			::= { hwMngmntHealth 81 } 

		hwFruFailDeassert NOTIFICATION-TYPE
			OBJECTS { hwTrapSeq, hwTrapSensorName, hwTrapEvent, hwTrapSeverity, hwTrapEventCode, hwTrapServerIdentity, hwTrapLocation, hwTrapTime }
			STATUS  current
			DESCRIPTION
				"FRU failure deassert"
			::= { hwMngmntHealth 82 }

	
	hwBattery OBJECT IDENTIFIER ::= {hwServerTRAPObject 41} 
    
		hwRTCBatterylow NOTIFICATION-TYPE
			OBJECTS { hwTrapSeq, hwTrapSensorName, hwTrapEvent, hwTrapSeverity, hwTrapEventCode, hwTrapServerIdentity, hwTrapLocation, hwTrapTime }
			STATUS  current
			DESCRIPTION
				"RTC battery or RAID card BBU voltage low"
			::= { hwBattery 1 }

		hwRTCBatterylowDeassert NOTIFICATION-TYPE
			OBJECTS { hwTrapSeq, hwTrapSensorName, hwTrapEvent, hwTrapSeverity, hwTrapEventCode, hwTrapServerIdentity, hwTrapLocation, hwTrapTime }
			STATUS  current
			DESCRIPTION
				"RTC battery or RAID card BBU voltage low deassert"
			::= { hwBattery 2 }

		hwRAIDCardBBUFailed NOTIFICATION-TYPE
			OBJECTS { hwTrapSeq, hwTrapSensorName, hwTrapEvent, hwTrapSeverity, hwTrapEventCode, hwTrapServerIdentity, hwTrapLocation, hwTrapTime }
			STATUS  current
			DESCRIPTION
				"RAID card BBU failed"
			::= { hwBattery 17 }

		hwRAIDCardBBUFailedDeassert NOTIFICATION-TYPE
			OBJECTS { hwTrapSeq, hwTrapSensorName, hwTrapEvent, hwTrapSeverity, hwTrapEventCode, hwTrapServerIdentity, hwTrapLocation, hwTrapTime }
			STATUS  current
			DESCRIPTION
				"RAID card BBU failure deassert"
			::= { hwBattery 18 } 
	  
		hwRAIDCardBBUPresence NOTIFICATION-TYPE
			OBJECTS { hwTrapSeq, hwTrapSensorName, hwTrapEvent, hwTrapSeverity, hwTrapEventCode, hwTrapServerIdentity, hwTrapLocation, hwTrapTime }
			STATUS  current
			DESCRIPTION
				"RAID card BBU is present"
			::= { hwBattery 33 }

		hwRAIDCardBBUPresenceDeassert NOTIFICATION-TYPE
			OBJECTS { hwTrapSeq, hwTrapSensorName, hwTrapEvent, hwTrapSeverity, hwTrapEventCode, hwTrapServerIdentity, hwTrapLocation, hwTrapTime }
			STATUS  current
			DESCRIPTION
				"RAID card BBU is absent"
			::= { hwBattery 34 }
	  
	hwVerChange OBJECT IDENTIFIER ::= {hwServerTRAPObject 43} 
    
		hwHardwareChange NOTIFICATION-TYPE
			OBJECTS { hwTrapSeq, hwTrapSensorName, hwTrapEvent, hwTrapSeverity, hwTrapEventCode, hwTrapServerIdentity, hwTrapLocation, hwTrapTime }
			STATUS  current
			DESCRIPTION
				"Hardware change detected with associated Entity"
			::= { hwVerChange 1 }

		hwFirmwareChange NOTIFICATION-TYPE
			OBJECTS { hwTrapSeq, hwTrapSensorName, hwTrapEvent, hwTrapSeverity, hwTrapEventCode, hwTrapServerIdentity, hwTrapLocation, hwTrapTime }
			STATUS  current
			DESCRIPTION
				"Firmware or software change detected with associated Entity"
			::= { hwVerChange 17 }

		hwFirmwareIncompatibility NOTIFICATION-TYPE
			OBJECTS { hwTrapSeq, hwTrapSensorName, hwTrapEvent, hwTrapSeverity, hwTrapEventCode, hwTrapServerIdentity, hwTrapLocation, hwTrapTime }
			STATUS  current
			DESCRIPTION
				"Firmware or software incompatibility detected with associated Entity"
			::= { hwVerChange 49 }

		hwFirmwareIncompatibilityDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Firmware or software incompatibility detected with associated Entity deassert"
			::= { hwVerChange 50 }

	hwLCD OBJECT IDENTIFIER ::= {hwServerTRAPObject 1052}  
    
		hwLCDFault NOTIFICATION-TYPE
			OBJECTS { hwTrapSeq, hwTrapSensorName, hwTrapEvent, hwTrapSeverity, hwTrapEventCode, hwTrapServerIdentity, hwTrapLocation, hwTrapTime }
			STATUS  current
			DESCRIPTION
				"LCD fault "
			::= { hwLCD 17 }

		hwLCDFaultDeassert NOTIFICATION-TYPE
			OBJECTS { hwTrapSeq, hwTrapSensorName, hwTrapEvent, hwTrapSeverity, hwTrapEventCode, hwTrapServerIdentity, hwTrapLocation, hwTrapTime }
			STATUS  current
			DESCRIPTION
				"LCD fault deassert"
			::= { hwLCD 18 }


	
	hwHotSwap OBJECT IDENTIFIER ::= {hwServerTRAPObject 240}
    
		hwHotSwaptoM0 NOTIFICATION-TYPE
			OBJECTS { hwTrapSeq, hwTrapSensorName, hwTrapEvent, hwTrapSeverity, hwTrapEventCode, hwTrapServerIdentity, hwTrapLocation, hwTrapTime }
			STATUS  current
			DESCRIPTION
				"fru hot swap to M0 status"
			::= { hwHotSwap 1 }

		hwHotSwaptoM1 NOTIFICATION-TYPE
			OBJECTS { hwTrapSeq, hwTrapSensorName, hwTrapEvent, hwTrapSeverity, hwTrapEventCode, hwTrapServerIdentity, hwTrapLocation, hwTrapTime }
			STATUS  current
			DESCRIPTION
				"fru hot swap to M1 status"
			::= { hwHotSwap 17 }

		hwHotSwaptoM2 NOTIFICATION-TYPE
			OBJECTS { hwTrapSeq, hwTrapSensorName, hwTrapEvent, hwTrapSeverity, hwTrapEventCode, hwTrapServerIdentity, hwTrapLocation, hwTrapTime }
			STATUS  current
			DESCRIPTION
				"fru hot swap to M2 status"
			::= { hwHotSwap 33 }

		hwHotSwaptoM3 NOTIFICATION-TYPE
			OBJECTS { hwTrapSeq, hwTrapSensorName, hwTrapEvent, hwTrapSeverity, hwTrapEventCode, hwTrapServerIdentity, hwTrapLocation, hwTrapTime }
			STATUS  current
			DESCRIPTION
				"fru hot swap to M3 status"
			::= { hwHotSwap 49 }

		hwHotSwaptoM4 NOTIFICATION-TYPE
			OBJECTS { hwTrapSeq, hwTrapSensorName, hwTrapEvent, hwTrapSeverity, hwTrapEventCode, hwTrapServerIdentity, hwTrapLocation, hwTrapTime }
			STATUS  current
			DESCRIPTION
				"fru hot swap to M4 status"
			::= { hwHotSwap 65 }

		hwHotSwaptoM5 NOTIFICATION-TYPE
			OBJECTS { hwTrapSeq, hwTrapSensorName, hwTrapEvent, hwTrapSeverity, hwTrapEventCode, hwTrapServerIdentity, hwTrapLocation, hwTrapTime }
			STATUS  current
			DESCRIPTION
				"fru hot swap to M5 status"
			::= { hwHotSwap 81 }

		hwHotSwaptoM6 NOTIFICATION-TYPE
			OBJECTS { hwTrapSeq, hwTrapSensorName, hwTrapEvent, hwTrapSeverity, hwTrapEventCode, hwTrapServerIdentity, hwTrapLocation, hwTrapTime }
			STATUS  current
			DESCRIPTION
				"fru hot swap to M6 status"
			::= { hwHotSwap 97 }

		hwHotSwaptoM7 NOTIFICATION-TYPE
			OBJECTS { hwTrapSeq, hwTrapSensorName, hwTrapEvent, hwTrapSeverity, hwTrapEventCode, hwTrapServerIdentity, hwTrapLocation, hwTrapTime }
			STATUS  current
			DESCRIPTION
				"fru hot swap to M7 status"
			::= { hwHotSwap 113 }

	
	hwIPMBLink OBJECT IDENTIFIER ::= {hwServerTRAPObject 241}
    
		hwIPMBLinkStateAll NOTIFICATION-TYPE
			OBJECTS { hwTrapSeq, hwTrapSensorName, hwTrapEvent, hwTrapSeverity, hwTrapEventCode, hwTrapServerIdentity, hwTrapLocation, hwTrapTime }
			STATUS  current
			DESCRIPTION
				"IPMB-A disabled. IPMB-B disabled"
			::= { hwIPMBLink 1 }

		hwIPMBLinkStateAllDeassert NOTIFICATION-TYPE
			OBJECTS { hwTrapSeq, hwTrapSensorName, hwTrapEvent, hwTrapSeverity, hwTrapEventCode, hwTrapServerIdentity, hwTrapLocation, hwTrapTime }
			STATUS  current
			DESCRIPTION
				"IPMB-A disabled. IPMB-B disabled deassert"
			::= { hwIPMBLink 2 }
      
		hwIPMBLinkStateB NOTIFICATION-TYPE
			OBJECTS { hwTrapSeq, hwTrapSensorName, hwTrapEvent, hwTrapSeverity, hwTrapEventCode, hwTrapServerIdentity, hwTrapLocation, hwTrapTime }
			STATUS  current
			DESCRIPTION
				"IPMB-A enabled.IPMB-B disabled"
			::= { hwIPMBLink 17 }

		hwIPMBLinkStateBDeassert NOTIFICATION-TYPE
			OBJECTS { hwTrapSeq, hwTrapSensorName, hwTrapEvent, hwTrapSeverity, hwTrapEventCode, hwTrapServerIdentity, hwTrapLocation, hwTrapTime }
			STATUS  current
			DESCRIPTION
				"IPMB-A enabled.IPMB-B disabled deassert"
			::= { hwIPMBLink 18 }

		hwIPMBLinkStateA NOTIFICATION-TYPE
			OBJECTS { hwTrapSeq, hwTrapSensorName, hwTrapEvent, hwTrapSeverity, hwTrapEventCode, hwTrapServerIdentity, hwTrapLocation, hwTrapTime }
			STATUS  current
			DESCRIPTION
				"IPMB-A disabled.IPMB-B enabled"
			::= { hwIPMBLink 33 }

		hwIPMBLinkStateADeassert NOTIFICATION-TYPE
			OBJECTS { hwTrapSeq, hwTrapSensorName, hwTrapEvent, hwTrapSeverity, hwTrapEventCode, hwTrapServerIdentity, hwTrapLocation, hwTrapTime }
			STATUS  current
			DESCRIPTION
				"IPMB-A disabled.IPMB-B enabled deassert"
			::= { hwIPMBLink 34 }

		hwIPMBLinkStateNoFault NOTIFICATION-TYPE
			OBJECTS { hwTrapSeq, hwTrapSensorName, hwTrapEvent, hwTrapSeverity, hwTrapEventCode, hwTrapServerIdentity, hwTrapLocation, hwTrapTime }
			STATUS  current
			DESCRIPTION
				"IPMB bus no fault"
			::= { hwIPMBLink 49 }
      
	
	hwTrapTest OBJECT IDENTIFIER ::= {hwServerTRAPObject 256}                         
		hwTrapTestInstance NOTIFICATION-TYPE
			OBJECTS { hwTrapSeq, hwTrapSensorName, hwTrapEvent, hwTrapSeverity, hwTrapEventCode, hwTrapServerIdentity, hwTrapLocation, hwTrapTime }
			STATUS  current
			DESCRIPTION
				"trap test"
			::= { hwTrapTest 1 }
      
	
	hwOvertemperature OBJECT IDENTIFIER ::= {hwServerTRAPObject 257}
                             
		hwOvertempMinor NOTIFICATION-TYPE
			OBJECTS { hwTrapSeq, hwTrapSensorName, hwTrapEvent, hwTrapSeverity, hwTrapEventCode, hwTrapServerIdentity, hwTrapLocation, hwTrapTime }
			STATUS  current
			DESCRIPTION
				"temperature above minor threshold"
			::= { hwOvertemperature 113 }  
      
		hwOvertempMinorDeassert NOTIFICATION-TYPE
			OBJECTS { hwTrapSeq, hwTrapSensorName, hwTrapEvent, hwTrapSeverity, hwTrapEventCode, hwTrapServerIdentity, hwTrapLocation, hwTrapTime }
			STATUS  current
			DESCRIPTION
				"temperature above minor threshold deassert"
			::= { hwOvertemperature 114 }  
      
		hwOvertempMajor NOTIFICATION-TYPE
			OBJECTS { hwTrapSeq, hwTrapSensorName, hwTrapEvent, hwTrapSeverity, hwTrapEventCode, hwTrapServerIdentity, hwTrapLocation, hwTrapTime }
			STATUS  current
			DESCRIPTION
				"temperature above major threshold"
			::= { hwOvertemperature 145 }  
      
		hwOvertempMajorDeassert NOTIFICATION-TYPE
			OBJECTS { hwTrapSeq, hwTrapSensorName, hwTrapEvent, hwTrapSeverity, hwTrapEventCode, hwTrapServerIdentity, hwTrapLocation, hwTrapTime }
			STATUS  current
			DESCRIPTION
				"temperature above major threshold deassert"
			::= { hwOvertemperature 146 }  
      
		hwOvertempCritical NOTIFICATION-TYPE
			OBJECTS { hwTrapSeq, hwTrapSensorName, hwTrapEvent, hwTrapSeverity, hwTrapEventCode, hwTrapServerIdentity, hwTrapLocation, hwTrapTime }
			STATUS  current
			DESCRIPTION
				"temperature above critical threshold"
			::= { hwOvertemperature 177 }  
      
		hwOvertempCriticalDeassert NOTIFICATION-TYPE
			OBJECTS { hwTrapSeq, hwTrapSensorName, hwTrapEvent, hwTrapSeverity, hwTrapEventCode, hwTrapServerIdentity, hwTrapLocation, hwTrapTime }
			STATUS  current
			DESCRIPTION
				"temperature above critical threshold deassert"
			::= { hwOvertemperature 178 }


	hwNoSDCard OBJECT IDENTIFIER ::= {hwServerTRAPObject 781}  
    
		hwNoSDCardAssert NOTIFICATION-TYPE
			OBJECTS { hwTrapSeq, hwTrapSensorName, hwTrapEvent, hwTrapSeverity, hwTrapEventCode, hwTrapServerIdentity, hwTrapLocation, hwTrapTime }
			STATUS  current
			DESCRIPTION
				"No SD Card Assert"
			::= { hwNoSDCard 17 }
	  
		hwNoSDCardDeassert NOTIFICATION-TYPE
			OBJECTS { hwTrapSeq, hwTrapSensorName, hwTrapEvent, hwTrapSeverity, hwTrapEventCode, hwTrapServerIdentity, hwTrapLocation, hwTrapTime }
			STATUS  current
			DESCRIPTION
				"No SD Card Deassert"
			::= { hwNoSDCard 18 }
            
	hwBoardMismatch OBJECT IDENTIFIER ::= {hwServerTRAPObject 786}  
		
		hwBoardMismatchAssert NOTIFICATION-TYPE
			OBJECTS { hwTrapSeq, hwTrapSensorName, hwTrapEvent, hwTrapSeverity, hwTrapEventCode, hwTrapServerIdentity, hwTrapLocation, hwTrapTime }
			STATUS  current
			DESCRIPTION
				"Board Mismatch Assert"
			::= { hwBoardMismatch 17 }
	  
		hwBoardMismatchDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Board Mismatch Deassert"
			::= { hwBoardMismatch 18 }
    
	hwAddInCard OBJECT IDENTIFIER ::= {hwServerTRAPObject 791}  
    
		hwPCIeError NOTIFICATION-TYPE
			OBJECTS { hwTrapSeq, hwTrapSensorName, hwTrapEvent, hwTrapSeverity, hwTrapEventCode, hwTrapServerIdentity, hwTrapLocation, hwTrapTime }
			STATUS  current
			DESCRIPTION
				"PCIe Error"
			::= { hwAddInCard 17 }
	  
		hwPCIeErrorDeassert NOTIFICATION-TYPE
			OBJECTS { hwTrapSeq, hwTrapSensorName, hwTrapEvent, hwTrapSeverity, hwTrapEventCode, hwTrapServerIdentity, hwTrapLocation, hwTrapTime }
			STATUS  current
			DESCRIPTION
				"PCIe Error Deassert"
			::= { hwAddInCard 18 }
	  
	hwChipSet OBJECT IDENTIFIER ::= {hwServerTRAPObject 793}  
    
		hwPCHError NOTIFICATION-TYPE
			OBJECTS { hwTrapSeq, hwTrapSensorName, hwTrapEvent, hwTrapSeverity, hwTrapEventCode, hwTrapServerIdentity, hwTrapLocation, hwTrapTime }
			STATUS  current
			DESCRIPTION
				"Uncorrectable PCH error"
			::= { hwChipSet 17 }
	  
		hwPCHErrorDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Uncorrectable PCH error Deassert"
			::= { hwChipSet 18 }
	
	hwUIDButton OBJECT IDENTIFIER ::= {hwServerTRAPObject 788}  
    
		hwUIDButtonPressed NOTIFICATION-TYPE
			OBJECTS { hwTrapSeq, hwTrapSensorName, hwTrapEvent, hwTrapSeverity, hwTrapEventCode, hwTrapServerIdentity, hwTrapLocation, hwTrapTime }
			STATUS  current
			DESCRIPTION
				"UID button pressed"
			::= { hwUIDButton 17 }


	
	hwPowerCapping OBJECT IDENTIFIER ::= {hwServerTRAPObject 1042}  
    
		hwPowerCapFail NOTIFICATION-TYPE
			OBJECTS { hwTrapSeq, hwTrapSensorName, hwTrapEvent, hwTrapSeverity, hwTrapEventCode, hwTrapServerIdentity, hwTrapLocation, hwTrapTime }
			STATUS  current
			DESCRIPTION
				"Power capping fail assert"
			::= { hwPowerCapping 17 }

		hwPowerCapFailDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Power capping fail deassert"
			::= { hwPowerCapping 18 }

	
	hwCardFault OBJECT IDENTIFIER ::= {hwServerTRAPObject 1047}  
    
		hwCardStatusFault NOTIFICATION-TYPE
			OBJECTS { hwTrapSeq, hwTrapSensorName, hwTrapEvent, hwTrapSeverity, hwTrapEventCode, hwTrapServerIdentity, hwTrapLocation, hwTrapTime }
			STATUS  current
			DESCRIPTION
				"RAID or NIC card fault"
			::= { hwCardFault 17 }

		hwCardStatusFaultDeassert NOTIFICATION-TYPE
			OBJECTS { hwTrapSeq, hwTrapSensorName, hwTrapEvent, hwTrapSeverity, hwTrapEventCode, hwTrapServerIdentity, hwTrapLocation, hwTrapTime }
			STATUS  current
			DESCRIPTION
				"RAID or NIC card fault deassert"
			::= { hwCardFault 18 }
      
	hwCPUUsage OBJECT IDENTIFIER ::= {hwServerTRAPObject 1287}  
    
		hwCPUUsageHigh NOTIFICATION-TYPE
			OBJECTS { hwTrapSeq, hwTrapSensorName, hwTrapEvent, hwTrapSeverity, hwTrapEventCode, hwTrapServerIdentity, hwTrapLocation, hwTrapTime }
			STATUS  current
			DESCRIPTION
				"CPU usage over threshold "
			::= { hwCPUUsage 17 }

		hwCPUUsageHighDeassert NOTIFICATION-TYPE
			OBJECTS { hwTrapSeq, hwTrapSensorName, hwTrapEvent, hwTrapSeverity, hwTrapEventCode, hwTrapServerIdentity, hwTrapLocation, hwTrapTime }
			STATUS  current
			DESCRIPTION
				"CPU usage over threshold deassert"
			::= { hwCPUUsage 18 }



	hwMemoryUsage OBJECT IDENTIFIER ::= {hwServerTRAPObject 1292}  
    
		hwMemoryUsageHigh NOTIFICATION-TYPE
			OBJECTS { hwTrapSeq, hwTrapSensorName, hwTrapEvent, hwTrapSeverity, hwTrapEventCode, hwTrapServerIdentity, hwTrapLocation, hwTrapTime }
			STATUS  current
			DESCRIPTION
				"Memory usage over threshold "
			::= { hwMemoryUsage 17 }

		hwMemoryUsageHighDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Memory usage over threshold deassert"
			::= { hwMemoryUsage 18 }


	hwDiskUsage OBJECT IDENTIFIER ::= {hwServerTRAPObject 1293}  
    
		hwDiskUsageHigh NOTIFICATION-TYPE
			OBJECTS { hwTrapSeq, hwTrapSensorName, hwTrapEvent, hwTrapSeverity, hwTrapEventCode, hwTrapServerIdentity, hwTrapLocation, hwTrapTime }
			STATUS  current
			DESCRIPTION
				"Disk usage over threshold "
			::= { hwDiskUsage 17 }

		hwDiskUsageHighDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Disk usage over threshold deassert"
			::= { hwDiskUsage 18 }

	hwLowPower OBJECT IDENTIFIER ::= {hwServerTRAPObject 1800}  
    
		hwPsInsufficient NOTIFICATION-TYPE
			OBJECTS { hwTrapSeq, hwTrapSensorName, hwTrapEvent, hwTrapSeverity, hwTrapEventCode, hwTrapServerIdentity, hwTrapLocation, hwTrapTime }
			STATUS  current
			DESCRIPTION
				"Insufficient power supply to the chassis"
			::= { hwLowPower 33 }
	  
		hwPsInsufficientDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Insufficient power supply to the chassis deassert"
			::= { hwLowPower 34 }
	  
	hwSysNotice OBJECT IDENTIFIER ::= {hwServerTRAPObject 1810}  
    
		hwSystemWarmReset NOTIFICATION-TYPE
			OBJECTS { hwTrapSeq, hwTrapSensorName, hwTrapEvent, hwTrapSeverity, hwTrapEventCode, hwTrapServerIdentity, hwTrapLocation, hwTrapTime }
			STATUS  current
			DESCRIPTION
				"Uncorrectable system error. Unable to locate the specific failure, please warm reset the host to try to solve the problem"
			::= { hwSysNotice 129 }
	  
		hwSystemWarmResetDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Uncorrectable system error deassert"
			::= { hwSysNotice 130 }
     
	hwModule OBJECT IDENTIFIER ::= {hwServerTRAPObject 1813}  
    
		hwModuleCritical NOTIFICATION-TYPE
			OBJECTS { hwTrapSeq, hwTrapSensorName, hwTrapEvent, hwTrapSeverity, hwTrapEventCode, hwTrapServerIdentity, hwTrapLocation, hwTrapTime }
			STATUS  current
			DESCRIPTION
				"transition to Critical from less severe"
			::= { hwModule 33 }
	
	hwPSPresenceStatus OBJECT IDENTIFIER ::= {hwServerTRAPObject 2057}  
    
		hwPSPresence NOTIFICATION-TYPE
			OBJECTS { hwTrapSeq, hwTrapSensorName, hwTrapEvent, hwTrapSeverity, hwTrapEventCode, hwTrapServerIdentity, hwTrapLocation, hwTrapTime }
			STATUS  current
			DESCRIPTION
				"power supply presence "
			::= { hwPSPresenceStatus 17 }

		hwPSPresenceDeassert NOTIFICATION-TYPE
			OBJECTS { hwTrapSeq, hwTrapSensorName, hwTrapEvent, hwTrapSeverity, hwTrapEventCode, hwTrapServerIdentity, hwTrapLocation, hwTrapTime }
			STATUS  current
			DESCRIPTION
				"power supply presence deassert"
			::= { hwPSPresenceStatus 18 }
	
	hwFanPresenceStatus OBJECT IDENTIFIER ::= {hwServerTRAPObject 2058}  
    
		hwFanAbsent NOTIFICATION-TYPE
			OBJECTS { hwTrapSeq, hwTrapSensorName, hwTrapEvent, hwTrapSeverity, hwTrapEventCode, hwTrapServerIdentity, hwTrapLocation, hwTrapTime }
			STATUS  current
			DESCRIPTION
				"fan absent "
			::= { hwFanPresenceStatus 1 }

		hwFanAbsentDeassert NOTIFICATION-TYPE
			OBJECTS { hwTrapSeq, hwTrapSensorName, hwTrapEvent, hwTrapSeverity, hwTrapEventCode, hwTrapServerIdentity, hwTrapLocation, hwTrapTime }
			STATUS  current
			DESCRIPTION
				"fan absent deassert"
			::= { hwFanPresenceStatus 2 }     

	
	hwCardPresenceStatus OBJECT IDENTIFIER ::= {hwServerTRAPObject 2071}  
    
		hwCardPresence NOTIFICATION-TYPE
			OBJECTS { hwTrapSeq, hwTrapSensorName, hwTrapEvent, hwTrapSeverity, hwTrapEventCode, hwTrapServerIdentity, hwTrapLocation, hwTrapTime }
			STATUS  current
			DESCRIPTION
				"card presence "
			::= { hwCardPresenceStatus 17 }

		hwCardPresenceDeassert NOTIFICATION-TYPE
			OBJECTS { hwTrapSeq, hwTrapSensorName, hwTrapEvent, hwTrapSeverity, hwTrapEventCode, hwTrapServerIdentity, hwTrapLocation, hwTrapTime }
			STATUS  current
			DESCRIPTION
				"card presence deassert"
			::= { hwCardPresenceStatus 18 }  

	hwLCDPresenceStatus OBJECT IDENTIFIER ::= {hwServerTRAPObject 2076}  
    
		hwLCDAbsent NOTIFICATION-TYPE
			OBJECTS { hwTrapSeq, hwTrapSensorName, hwTrapEvent, hwTrapSeverity, hwTrapEventCode, hwTrapServerIdentity, hwTrapLocation, hwTrapTime }
			STATUS  current
			DESCRIPTION
				"LCD absent"
			::= { hwLCDPresenceStatus 1 }

		hwLCDAbsentDeassert NOTIFICATION-TYPE
			OBJECTS { hwTrapSeq, hwTrapSensorName, hwTrapEvent, hwTrapSeverity, hwTrapEventCode, hwTrapServerIdentity, hwTrapLocation, hwTrapTime }
			STATUS  current
			DESCRIPTION
				"LCD absent deassert"
			::= { hwLCDPresenceStatus 2 }  	  
	  
	hwMemoryRiser OBJECT IDENTIFIER ::= {hwServerTRAPObject 2583}    	
		hwMemoryRiserOnline NOTIFICATION-TYPE
			OBJECTS { hwTrapSeq, hwTrapSensorName, hwTrapEvent, hwTrapSeverity, hwTrapEventCode, hwTrapServerIdentity, hwTrapLocation, hwTrapTime }
			STATUS  current
			DESCRIPTION
				"Memory board online "
			::= { hwMemoryRiser 49 }

		hwMemoryRiserOnlineDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Memory board online deassert"
			::= { hwMemoryRiser 50 }

		hwMemoryRiserOffline NOTIFICATION-TYPE
			OBJECTS { hwTrapSeq, hwTrapSensorName, hwTrapEvent, hwTrapSeverity, hwTrapEventCode, hwTrapServerIdentity, hwTrapLocation, hwTrapTime }
			STATUS  current
			DESCRIPTION
				"Memory board offline "
			::= { hwMemoryRiser 65 }

		hwMemoryRiserOfflineDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Memory board offline deassert"
			::= { hwMemoryRiser 66 }
      
		hwMemoryRiserInstallError NOTIFICATION-TYPE
			OBJECTS { hwTrapSeq, hwTrapSensorName, hwTrapEvent, hwTrapSeverity, hwTrapEventCode, hwTrapServerIdentity, hwTrapLocation, hwTrapTime }
			STATUS  current
			DESCRIPTION
				"Memory riser install error "
			::= { hwMemoryRiser 129 }

		hwMemoryRiserInstallErrorDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Memory riser install error deassert"
			::= { hwMemoryRiser 130 }

      
	hwCPUCore OBJECT IDENTIFIER ::= {hwServerTRAPObject 2311}
    
		hwCPUCoreIsolation NOTIFICATION-TYPE
			OBJECTS { hwTrapSeq, hwTrapSensorName, hwTrapEvent, hwTrapSeverity, hwTrapEventCode, hwTrapServerIdentity, hwTrapLocation, hwTrapTime }
			STATUS  current
			DESCRIPTION
				"CPU core isolation"
			::= { hwCPUCore 1 }

		hwCPUCoreIsolationDeassert NOTIFICATION-TYPE
			OBJECTS { hwTrapSeq, hwTrapSensorName, hwTrapEvent, hwTrapSeverity, hwTrapEventCode, hwTrapServerIdentity, hwTrapLocation, hwTrapTime }
			STATUS  current
			DESCRIPTION
				"CPU core isolation deassert"
			::= { hwCPUCore 2 }
	  
	hwPSRedundancy OBJECT IDENTIFIER ::= {hwServerTRAPObject 2824}
    
		hwPSRedundancyLost NOTIFICATION-TYPE
			OBJECTS { hwTrapSeq, hwTrapSensorName, hwTrapEvent, hwTrapSeverity, hwTrapEventCode, hwTrapServerIdentity, hwTrapLocation, hwTrapTime }
			STATUS  current
			DESCRIPTION
				"PS Redundancy lost"
			::= { hwPSRedundancy 17 }

		hwPSRedundancyLostDeassert NOTIFICATION-TYPE
			OBJECTS { hwTrapSeq, hwTrapSensorName, hwTrapEvent, hwTrapSeverity, hwTrapEventCode, hwTrapServerIdentity, hwTrapLocation, hwTrapTime }
			STATUS  current
			DESCRIPTION
				"PS Redundancy lost deassert"
			::= { hwPSRedundancy 18 }
      
	hwSELStatus OBJECT IDENTIFIER ::= {hwServerTRAPObject 16}  
    
		hwSELClearedAssert NOTIFICATION-TYPE
			OBJECTS { hwTrapSeq, hwTrapSensorName, hwTrapEvent, hwTrapSeverity, hwTrapEventCode, hwTrapServerIdentity, hwTrapLocation, hwTrapTime }
			STATUS  current
			DESCRIPTION
				"SEL log area is cleared"
			::= { hwSELStatus 33 }
	  
		hwSELAlmostFullAssert NOTIFICATION-TYPE
			OBJECTS { hwTrapSeq, hwTrapSensorName, hwTrapEvent, hwTrapSeverity, hwTrapEventCode, hwTrapServerIdentity, hwTrapLocation, hwTrapTime }
			STATUS  current
			DESCRIPTION
				"SEL almost full assert"
			::= { hwSELStatus 81 }

		hwSELAlmostFullDeassert NOTIFICATION-TYPE
			OBJECTS { hwTrapSeq, hwTrapSensorName, hwTrapEvent, hwTrapSeverity, hwTrapEventCode, hwTrapServerIdentity, hwTrapLocation, hwTrapTime }
			STATUS  current
			DESCRIPTION
				"SEL almost full deassert"
			::= { hwSELStatus 82 }

	hwBMCBootUp OBJECT IDENTIFIER ::= {hwServerTRAPObject 2326}  
    
		hwBMCBootUpAssert NOTIFICATION-TYPE
			OBJECTS { hwTrapSeq, hwTrapSensorName, hwTrapEvent, hwTrapSeverity, hwTrapEventCode, hwTrapServerIdentity, hwTrapLocation, hwTrapTime }
			STATUS  current
			DESCRIPTION
				"BMC boot up"
			::= { hwBMCBootUp 17 }

	hwLog OBJECT IDENTIFIER ::= {hwServerTRAPObject 1808}  
      
		hwLogFull NOTIFICATION-TYPE
			OBJECTS { hwTrapSeq, hwTrapSensorName, hwTrapEvent, hwTrapSeverity, hwTrapEventCode, hwTrapServerIdentity, hwTrapLocation, hwTrapTime }
			STATUS  current
			DESCRIPTION
				"Informational"
			::= { hwLog 129 }

		hwLogFullDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Informational deassert"
			::= { hwLog 130 }
	
	hwVoltage OBJECT IDENTIFIER ::= {hwServerTRAPObject 258} 

		hwLowerVoltageMajor NOTIFICATION-TYPE
			OBJECTS { hwTrapSeq, hwTrapSensorName, hwTrapEvent, hwTrapSeverity, hwTrapEventCode, hwTrapServerIdentity, hwTrapLocation, hwTrapTime }
			STATUS  current
			DESCRIPTION
				"Voltage below lower major threshold"
			::= { hwVoltage 33 }  
      
		hwLowerVoltageMajorDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Voltage below lower major threshold deassert"
			::= { hwVoltage 34 }  

		hwOverVoltageMajor NOTIFICATION-TYPE
			OBJECTS { hwTrapSeq, hwTrapSensorName, hwTrapEvent, hwTrapSeverity, hwTrapEventCode, hwTrapServerIdentity, hwTrapLocation, hwTrapTime }
			STATUS  current
			DESCRIPTION
				"Voltage over upper major threshold"
			::= { hwVoltage 145 }

		hwOverVoltageMajorDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Voltage over upper major threshold deassert"
			::= { hwVoltage 146 }
      
		hwOverVoltageCritcal NOTIFICATION-TYPE
			OBJECTS { hwTrapSeq, hwTrapSensorName, hwTrapEvent, hwTrapSeverity, hwTrapEventCode, hwTrapServerIdentity, hwTrapLocation, hwTrapTime }
			STATUS  current
			DESCRIPTION
				"Voltage over upper critcal threshold"
			::= { hwVoltage 177 }

		hwOverVoltageCritcalDeassert NOTIFICATION-TYPE
			OBJECTS { hwTrapSeq, hwTrapSensorName, hwTrapEvent, hwTrapSeverity, hwTrapEventCode, hwTrapServerIdentity, hwTrapLocation, hwTrapTime }
			STATUS  current
			DESCRIPTION
				"Voltage over upper critcal threshold deassert"
			::= { hwVoltage 178 }

	hwCPUProchot OBJECT IDENTIFIER ::= {hwServerTRAPObject 775} 

		hwCPUProchotState NOTIFICATION-TYPE
			OBJECTS { hwTrapSeq, hwTrapSensorName, hwTrapEvent, hwTrapSeverity, hwTrapEventCode, hwTrapServerIdentity, hwTrapLocation, hwTrapTime }
			STATUS  current
			DESCRIPTION
				"CPU Prochot state asserted"
			::= { hwCPUProchot 17 }  
      
		hwCPUProchotStateDeassert NOTIFICATION-TYPE
			OBJECTS { hwTrapSeq, hwTrapSensorName, hwTrapEvent, hwTrapSeverity, hwTrapEventCode, hwTrapServerIdentity, hwTrapLocation, hwTrapTime }
			STATUS  current
			DESCRIPTION
				"CPU Prochot state deasserted"
			::= { hwCPUProchot 18 }  
--		****** hwServerTRAPObject End ******
--		****** hwServerTRAPObjectV2 Begin ******
	hwServerTRAPObjectV2 OBJECT IDENTIFIER ::= { hwTrap 11 }
	hwCPUEvent OBJECT IDENTIFIER ::= {hwServerTRAPObjectV2 1 }
		hwCPUOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU underclocking will be caused by high temperature. (Generated)"
			::= { hwCPUEvent 3 }
		hwCPUOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU underclocking will be caused by high temperature. (Cleared)"
			::= { hwCPUEvent 4 }
		hwCPUVDDQOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VDDQ overheating minor alarm. (Generated)"
			::= { hwCPUEvent 5 }
		hwCPUVDDQOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VDDQ overheating minor alarm. (Cleared)"
			::= { hwCPUEvent 6 }
		hwCPUVRDOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VRD overheating minor alarm. (Generated)"
			::= { hwCPUEvent 7 }
		hwCPUVRDOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VRD overheating minor alarm. (Cleared)"
			::= { hwCPUEvent 8 }
		hwCPUCoreLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU undervoltage major alarm. (Generated)"
			::= { hwCPUEvent 11 }
		hwCPUCoreLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU undervoltage major alarm. (Cleared)"
			::= { hwCPUEvent 12 }
		hwCPUCoreOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU overvoltage major alarm. (Generated)"
			::= { hwCPUEvent 13 }
		hwCPUCoreOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU overvoltage major alarm. (Cleared)"
			::= { hwCPUEvent 14 }
		hwCPUOverTempCritical NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The OS was shut down due to CPU overheating. (Generated)"
			::= { hwCPUEvent 15 }
		hwCPUOverTempCriticalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The OS was shut down due to CPU overheating. (Cleared)"
			::= { hwCPUEvent 16 }
		hwCPUSelfTestFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU self-test failed. (Generated)"
			::= { hwCPUEvent 17 }
		hwCPUSelfTestFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU self-test failed. (Cleared)"
			::= { hwCPUEvent 18 }
		hwCPUCFGError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect CPU configuration. (Generated)"
			::= { hwCPUEvent 19 }
		hwCPUCFGErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect CPU configuration. (Cleared)"
			::= { hwCPUEvent 20 }
		hwCPUInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU installed."
			::= { hwCPUEvent 21 }
		hwCPURemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU removed."
			::= { hwCPUEvent 23 }
		hwCPULowerDiffTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The CPU is about to reach the Max. temperature of minor alarm. (Generated)"
			::= { hwCPUEvent 25 }
		hwCPULowerDiffTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The CPU is about to reach the Max. temperature of minor alarm. (Cleared)"
			::= { hwCPUEvent 26 }
		hwCPUIerrFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU IERR error. (Generated)"
			::= { hwCPUEvent 27 }
		hwCPUIerrFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU IERR error. (Cleared)"
			::= { hwCPUEvent 28 }
		hwCPUUncorrectableErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU MCE/AER error. (Generated)"
			::= { hwCPUEvent 29 }
		hwCPUUncorrectableErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU MCE/AER error. (Cleared)"
			::= { hwCPUEvent 30 }
		hwCPUCoreIsolated NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU core isolated. (Generated)"
			::= { hwCPUEvent 31 }
		hwCPUCoreIsolatedDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU core isolated. (Cleared)"
			::= { hwCPUEvent 32 }
		hwCPUFaultyIsolated NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU isolated. (Generated)"
			::= { hwCPUEvent 33 }
		hwCPUFaultyIsolatedDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU isolated. (Cleared)"
			::= { hwCPUEvent 34 }
		hwCPUAccessCoreTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU core temperature. (Generated)"
			::= { hwCPUEvent 35 }
		hwCPUAccessCoreTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU core temperature. (Cleared)"
			::= { hwCPUEvent 36 }
		hwCPUAccessVDDQTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU VDDQ temperature. (Generated)"
			::= { hwCPUEvent 37 }
		hwCPUAccessVDDQTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU VDDQ temperature. (Cleared)"
			::= { hwCPUEvent 38 }
		hwCPUVRDOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VRD overheating major alarm. (Generated)"
			::= { hwCPUEvent 39 }
		hwCPUVRDOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VRD overheating major alarm. (Cleared)"
			::= { hwCPUEvent 40 }
		hwCPULowerDiffTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU temperature is about to reach the upper major threshold. (Generated)"
			::= { hwCPUEvent 41 }
		hwCPULowerDiffTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU temperature is about to reach the upper major threshold. (Cleared)"
			::= { hwCPUEvent 42 }
		hwCPUMIMC0CH0MirrorFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 0, iMC 0 of CPU. (Generated)"
			::= { hwCPUEvent 43 }
		hwCPUMIMC0CH0MirrorFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 0, iMC 0 of CPU. (Cleared)"
			::= { hwCPUEvent 44 }
		hwCPUMIMC0CH1MirrorFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 1, iMC 0 of CPU. (Generated)"
			::= { hwCPUEvent 45 }
		hwCPUMIMC0CH1MirrorFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 1, iMC 0 of CPU. (Cleared)"
			::= { hwCPUEvent 46 }
		hwCPUMIMC0CH2MirrorFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 2, iMC 0 of CPU. (Generated)"
			::= { hwCPUEvent 47 }
		hwCPUMIMC0CH2MirrorFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 2, iMC 0 of CPU. (Cleared)"
			::= { hwCPUEvent 48 }
		hwCPUMIMC0CH3MirrorFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 3, iMC 0 of CPU. (Generated)"
			::= { hwCPUEvent 49 }
		hwCPUMIMC0CH3MirrorFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 3, iMC 0 of CPU. (Cleared)"
			::= { hwCPUEvent 50 }
		hwCPUMIMC1CH0MirrorFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 0, iMC 1 of CPU. (Generated)"
			::= { hwCPUEvent 51 }
		hwCPUMIMC1CH0MirrorFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 0, iMC 1 of CPU. (Cleared)"
			::= { hwCPUEvent 52 }
		hwCPUMIMC1CH1MirrorFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 1, iMC 1 of CPU. (Generated)"
			::= { hwCPUEvent 53 }
		hwCPUMIMC1CH1MirrorFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 1, iMC 1 of CPU. (Cleared)"
			::= { hwCPUEvent 54 }
		hwCPUMIMC1CH2MirrorFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 2, iMC 1 of CPU. (Generated)"
			::= { hwCPUEvent 55 }
		hwCPUMIMC1CH2MirrorFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 2, iMC 1 of CPU. (Cleared)"
			::= { hwCPUEvent 56 }
		hwCPUMIMC1CH3MirrorFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 3, iMC 1 of CPU. (Generated)"
			::= { hwCPUEvent 57 }
		hwCPUMIMC1CH3MirrorFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory mirroring failed in channel 3, iMC 1 of CPU. (Cleared)"
			::= { hwCPUEvent 58 }
		hwCPUAccessDTSTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU DTS temperature. (Generated)"
			::= { hwCPUEvent 59 }
		hwCPUAccessDTSTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU DTS temperature. (Cleared)"
			::= { hwCPUEvent 60 }
		hwCPUVCCPOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VCCP overvoltage. (Generated)"
			::= { hwCPUEvent 61 }
		hwCPUVCCPOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VCCP overvoltage. (Cleared)"
			::= { hwCPUEvent 62 }
		hwCPUVCCPLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VCCP undervoltage. (Generated)"
			::= { hwCPUEvent 63 }
		hwCPUVCCPLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VCCP undervoltage. (Cleared)"
			::= { hwCPUEvent 64 }
		hwCPUAccessVCCPVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU VCCP voltage. (Generated)"
			::= { hwCPUEvent 65 }
		hwCPUAccessVCCPVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU VCCP voltage. (Cleared)"
			::= { hwCPUEvent 66 }		
		hwCPUVSAOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VSA overvoltage. (Generated)"
			::= { hwCPUEvent 79 }
		hwCPUVSAOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VSA overvoltage. (Cleared)"
			::= { hwCPUEvent 80 }
		hwCPUVSALowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VSA undervoltage. (Generated)"
			::= { hwCPUEvent 81 }
		hwCPUVSALowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VSA undervoltage. (Cleared)"
			::= { hwCPUEvent 82 }
		hwCPUAccessVSAVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU VSA voltage. (Generated)"
			::= { hwCPUEvent 83 }
		hwCPUAccessVSAVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU VSA voltage. (Cleared)"
			::= { hwCPUEvent 84 }
		hwCPUVCCIOOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VCCIO overvoltage. (Generated)"
			::= { hwCPUEvent 85 }
		hwCPUVCCIOOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VCCIO overvoltage. (Cleared)"
			::= { hwCPUEvent 86 }
		hwCPUVCCIOLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VCCIO undervoltage. (Generated)"
			::= { hwCPUEvent 87 }
		hwCPUVCCIOLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VCCIO undervoltage. (Cleared)"
			::= { hwCPUEvent 88 }
		hwCPUAccessVCCIOVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU VCCIO voltage. (Generated)"
			::= { hwCPUEvent 89 }
		hwCPUAccessVCCIOVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU VCCIO voltage. (Cleared)"
			::= { hwCPUEvent 90 }
		hwCPUVMCPOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VMCP overvoltage. (Generated)"
			::= { hwCPUEvent 91 }
		hwCPUVMCPOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VMCP overvoltage. (Cleared)"
			::= { hwCPUEvent 92 }
		hwCPUVMCPLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VMCP undervoltage. (Generated)"
			::= { hwCPUEvent 93 }
		hwCPUVMCPLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VMCP undervoltage. (Cleared)"
			::= { hwCPUEvent 94 }
		hwCPUAccessVMCPVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU VMCP voltage. (Generated)"
			::= { hwCPUEvent 95 }
		hwCPUAccessVMCPVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU VMCP voltage. (Cleared)"
			::= { hwCPUEvent 96 }
		hwCPUAccessVRDTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU VRD temperature. (Generated)"
			::= { hwCPUEvent 97 }
		hwCPUAccessVRDTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU VRD temperature. (Cleared)"
			::= { hwCPUEvent 98 }
		hwCPUAccessCoreVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU Core voltage. (Generated)"
			::= { hwCPUEvent 99 }
		hwCPUAccessCoreVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU Core voltage. (Cleared)"
			::= { hwCPUEvent 100 }
		hwCPUVoltLow NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU undervoltage. (Generated)"
			::= { hwCPUEvent 101 }
		hwCPUVoltLowDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU undervoltage. (Cleared)"
			::= { hwCPUEvent 102 }
		hwCPUVoltHigh NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU overvoltage. (Generated)"
			::= { hwCPUEvent 103 }
		hwCPUVoltHighDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU overvoltage. (Cleared)"
			::= { hwCPUEvent 104 }
		hwCPUVDDQOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VDDQ overheating major alarm. (Generated)"
			::= { hwCPUEvent 105 }
		hwCPUVDDQOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU VDDQ overheating major alarm. (Cleared)"
			::= { hwCPUEvent 106 }
		hwCPUMarginFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU margin. (Generated)"
			::= { hwCPUEvent 107 }
		hwCPUMarginFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU margin. (Cleared)"
			::= { hwCPUEvent 108 }
		hwCPUCoreOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The CPU core temperature exceeds the overtemperature threshold. (Generated)"
			::= { hwCPUEvent 109 }
		hwCPUCoreOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The CPU core temperature exceeds the overtemperature threshold. (Cleared)"
			::= { hwCPUEvent 110 }
			
		hwCPUNimbusLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU Nimbus voltage is lower than the undervoltage threshold. (Generated)"
			::= { hwCPUEvent 111 }
		hwCPUNimbusLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU Nimbus voltage is lower than the undervoltage threshold. (Cleared)"
			::= { hwCPUEvent 112 }
			
		hwCPUNimbusOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU Nimbus voltage exceeds the overvoltage threshold. (Generated)"
			::= { hwCPUEvent 113 }
		hwCPUNimbusOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU Nimbus voltage exceeds the overvoltage threshold. (Cleared)"
			::= { hwCPUEvent 114 }  
			    
		hwCPUAbsence NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to start the system. CPU 1 was not detected. "
			::= { hwCPUEvent 115 } 

		hwCPUNVRHot NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU has a vr hot error. (Generated)"
			::= { hwCPUEvent 117 }
		hwCPUNVRHotDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU has a vr hot error. (Cleared)"
			::= { hwCPUEvent 118 }
		hwCPUNVDDQVRHot NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU has a vddq hot error. (Generated)"
			::= { hwCPUEvent 119 } 
		hwCPUNVDDQVRHotDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU has a vddq hot error. (Cleared)"
			::= { hwCPUEvent 120 }
		hwCPUCEHardFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU health status degradation detected by PFAE. (Generated)"
			::= { hwCPUEvent 121 }
		hwCPUCEHardFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU health status degradation detected by PFAE. (Cleared)"
			::= { hwCPUEvent 122 }
		hwCPUReplaced  NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU is replaced. (Generated)"
			::= { hwCPUEvent 129 }			
		hwCPUPCIeMMIOErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PCIe MMIO configuration space in CPU is insufficient. (Generated)"
			::= { hwCPUEvent 131 } 
		hwCPUPCIeMMIOErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PCIe MMIO configuration space in CPU is insufficient. (Cleared)"
			::= { hwCPUEvent 132 }
	hwMemoryEvent OBJECT IDENTIFIER ::= {hwServerTRAPObjectV2 2 }
		hwMemoryOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM overheating major alarm. (Generated)"
			::= { hwMemoryEvent 1 }
		hwMemoryOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM overheating major alarm. (Cleared)"
			::= { hwMemoryEvent 2 }
		hwMemoryVDDQ1LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM VDDQ1 undervoltage major alarm. (Generated)"
			::= { hwMemoryEvent 3 }
		hwMemoryVDDQ1LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM VDDQ1 undervoltage major alarm. (Cleared)"
			::= { hwMemoryEvent 4 }
		hwMemoryVDDQ1OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM VDDQ1 overvoltage major alarm. (Generated)"
			::= { hwMemoryEvent 5 }
		hwMemoryVDDQ1OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM VDDQ1 overvoltage major alarm. (Cleared)"
			::= { hwMemoryEvent 6 }
		hwMemoryVDDQ2LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM VDDQ2 undervoltage major alarm. (Generated)"
			::= { hwMemoryEvent 7 }
		hwMemoryVDDQ2LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM VDDQ2 undervoltage major alarm. (Cleared)"
			::= { hwMemoryEvent 8 }
		hwMemoryVDDQ2OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM VDDQ2 overvoltage major alarm. (Generated)"
			::= { hwMemoryEvent 9 }
		hwMemoryVDDQ2OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM VDDQ2 overvoltage major alarm. (Cleared)"
			::= { hwMemoryEvent 10 }
		hwMemoryCorrectableECC NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM ECC error count exceeded. (Generated)"
			::= { hwMemoryEvent 13 }
		hwMemoryCorrectableECCDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM ECC error count exceeded. (Cleared)"
			::= { hwMemoryEvent 14 }
		hwMemoryInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM installed."
			::= { hwMemoryEvent 15 }
		hwMemoryRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM removed."
			::= { hwMemoryEvent 17 }
		hwMemoryCFGErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect memory configuration. (Generated)"
			::= { hwMemoryEvent 21 }
		hwMemoryCFGErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect memory configuration. (Cleared)"
			::= { hwMemoryEvent 22 }
		hwMemoryUncorrectableErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM MCE error. (Generated)"
			::= { hwMemoryEvent 23 }
		hwMemoryUncorrectableErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM MCE error. (Cleared)"
			::= { hwMemoryEvent 24 }
		hwMemoryVPP1LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM VPP1 undervoltage major alarm. (Generated)"
			::= { hwMemoryEvent 25 }
		hwMemoryVPP1LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM VPP1 undervoltage major alarm. (Cleared)"
			::= { hwMemoryEvent 26 }
		hwMemoryVPP1OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM VPP1 overvoltage major alarm. (Generated)"
			::= { hwMemoryEvent 27 }
		hwMemoryVPP1OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM VPP1 overvoltage major alarm. (Cleared)"
			::= { hwMemoryEvent 28 }
		hwMemorySwitchToStdbyBoard NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMMs go standby. (Generated)"
			::= { hwMemoryEvent 29 }
		hwMemorySwitchToStdbyBoardDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMMs go standby. (Cleared)"
			::= { hwMemoryEvent 30 }
		hwMemoryVDDQ1AccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read DIMM VDDQ1 voltage. (Generated)"
			::= { hwMemoryEvent 31 }
		hwMemoryVDDQ1AccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read DIMM VDDQ1 voltage. (Cleared)"
			::= { hwMemoryEvent 32 }
		hwMemoryVDDQ2AccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read DIMM VDDQ2 voltage. (Generated)"
			::= { hwMemoryEvent 33 }
		hwMemoryVDDQ2AccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read DIMM VDDQ2 voltage. (Cleared)"
			::= { hwMemoryEvent 34 }
		hwMemoryVPP1AccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read DIMM VPP1 voltage. (Generated)"
			::= { hwMemoryEvent 35 }
		hwMemoryVPP1AccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read DIMM VPP1 voltage. (Cleared)"
			::= { hwMemoryEvent 36 }
		hwMemoryConfigError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect memory configuration. (Generated)"
			::= { hwMemoryEvent 37 }
		hwMemoryConfigErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect memory configuration. (Cleared)"
			::= { hwMemoryEvent 38 }
		hwMemoryInitializationError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory initialization error. (Generated)"
			::= { hwMemoryEvent 39 }
		hwMemoryInitializationErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory initialization error. (Cleared)"
			::= { hwMemoryEvent 40 }
		hwMemoryCEHardFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory CE hard failure. (Generated)"
			::= { hwMemoryEvent 45 }
		hwMemoryCEHardFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory CE hard failure. (Cleared)"
			::= { hwMemoryEvent 46 }
		hwMemoryMRCFatalError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory MRC fatal error. (Generated)"
			::= { hwMemoryEvent 47 }
		hwMemoryMRCFatalErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory MRC fatal error. (Cleared)"
			::= { hwMemoryEvent 48 }
		hwMemoryVPP2OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory VPP2 overvoltage. (Generated)"
			::= { hwMemoryEvent 51 }
		hwMemoryVPP2OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory VPP2 overvoltage. (Cleared)"
			::= { hwMemoryEvent 52 }
		hwMemoryVPP2LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory VPP2 undervoltage. (Generated)"
			::= { hwMemoryEvent 53 }
		hwMemoryVPP2LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory VPP2 undervoltage. (Cleared)"
			::= { hwMemoryEvent 54 }
		hwMemoryAccessVPP2VoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read the memory VPP2 voltage. (Generated)"
			::= { hwMemoryEvent 55 }
		hwMemoryAccessVPP2VoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read the memory VPP2 voltage. (Cleared)"
			::= { hwMemoryEvent 56 }
		hwMemoryOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory overtemperature minor alarm. (Generated)"
			::= { hwMemoryEvent 59 }
		hwMemoryOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory overtemperature minor alarm. (Cleared)"
			::= { hwMemoryEvent 60 }
		hwMemoryOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory overtemperature major alarm. (Generated)"
			::= { hwMemoryEvent 61 }
		hwMemoryOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory overtemperature major alarm. (Cleared)"
			::= { hwMemoryEvent 62 }
		hwMemoryAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read memory temperature. (Generated)"
			::= { hwMemoryEvent 63 }
		hwMemoryAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read memory temperature. (Cleared)"
			::= { hwMemoryEvent 64 }
		hwMemoryReplaced NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory is replaced. (Generated)"
			::= { hwMemoryEvent 65 }
		hwMemoryNVDIMMCapacitorAbsent NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NVDIMM supercapacitor is absent. (Generated)"
			::= { hwMemoryEvent 67 }
		hwMemoryNVDIMMCapacitorAbsentDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NVDIMM supercapacitor is absent. (Cleared)"
			::= { hwMemoryEvent 68 }
		hwMemoryDCPMMOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DCPMM overtemperature minor alarm. (Generated)"
			::= { hwMemoryEvent 69 }
		hwMemoryDCPMMOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DCPMM overtemperature minor alarm. (Cleared)"
			::= { hwMemoryEvent 70 }
		hwMemoryDCPMMAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read DCPMM temperature. (Generated)"
			::= { hwMemoryEvent 71 }
		hwMemoryDCPMMAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read DCPMM temperature. (Cleared)"
			::= { hwMemoryEvent 72 }
		hwMemoryNVDIMMSlotMismatch NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NVDIMM slot mismatch. (Generated)"
			::= { hwMemoryEvent 73 }
		hwMemoryNVDIMMSlotMismatchDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NVDIMM slot mismatch. (Cleared)"
			::= { hwMemoryEvent 74 }
		hwMemoryNVDIMMDataRestorationFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NVDIMM data restoration failure. (Generated)"
			::= { hwMemoryEvent 75 }
		hwMemoryNVDIMMDataRestorationFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NVDIMM data restoration failure. (Cleared)"
			::= { hwMemoryEvent 76 }
		hwMemoryDCPMMNoncriticalFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DCPMM has a noncritical fault. (Generated)"
			::= { hwMemoryEvent 77 }
		hwMemoryDCPMMNoncriticalFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DCPMM has a noncritical fault. (Cleared)"
			::= { hwMemoryEvent 78 }
		hwMemoryDCPMMCriticalFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DCPMM has a critical fault. (Generated)"
			::= { hwMemoryEvent 79 }
		hwMemoryDCPMMCriticalFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DCPMM has a critical fault. (Cleared)"
			::= { hwMemoryEvent 80 }
		hwMemoryInstallationError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory installation error. (Generated)"
			::= { hwMemoryEvent 81 }
		hwMemoryInstallationErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory installation error. (Cleared)"
			::= { hwMemoryEvent 82 }
		hwMemoryDCPMMMajorFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DCPMM has a major fault. (Generated)"
			::= { hwMemoryEvent 83 }
		hwMemoryDCPMMMajorFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DCPMM has a major fault. (Cleared)"
			::= { hwMemoryEvent 84 }
	hwDiskEvent OBJECT IDENTIFIER ::= {hwServerTRAPObjectV2 3 }
		hwDiskInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk installed."
			::= { hwDiskEvent 3 }
		hwDiskRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk removed."
			::= { hwDiskEvent 5 }
		hwDiskFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk fault. (Generated)"
			::= { hwDiskEvent 7 }
		hwDiskFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk fault. (Cleared)"
			::= { hwDiskEvent 8 }
		hwDiskPredictiveFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk predictive fault. (Generated)"
			::= { hwDiskEvent 9 }
		hwDiskPredictiveFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk predictive fault. (Cleared)"
			::= { hwDiskEvent 10 }
		hwDiskRAIDArrayInvalid NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID array invalid. (Generated)"
			::= { hwDiskEvent 11 }
		hwDiskRAIDArrayInvalidDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID array invalid. (Cleared)"
			::= { hwDiskEvent 12 }
		hwDiskRAIDRebuildStart NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Starting to rebuild RAID."
			::= { hwDiskEvent 13 }
		hwDiskRAIDRebuildStop NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk RAID rebuild stopped."
			::= { hwDiskEvent 15 }
		hwDiskUncorrectableErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk MCE/AER error. (Generated)"
			::= { hwDiskEvent 19 }
		hwDiskUncorrectableErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk MCE/AER error. (Cleared)"
			::= { hwDiskEvent 20 }
		hwDiskOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk overheating minor alarm. (Generated)"
			::= { hwDiskEvent 21 }
		hwDiskOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk overheating minor alarm. (Cleared)"
			::= { hwDiskEvent 22 }
		hwDiskAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read hard disk temperature. (Generated)"
			::= { hwDiskEvent 23 }
		hwDiskAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read hard disk temperature. (Cleared)"
			::= { hwDiskEvent 24 }
		hwDiskOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk overheating major alarm. (Generated)"
			::= { hwDiskEvent 25 }
		hwDiskOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk overheating major alarm. (Cleared)"
			::= { hwDiskEvent 26 }
		hwDiskPwrFailMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The power signal of the disk is abnormal. (Generated)"
			::= { hwDiskEvent 27 }
		hwDiskPwrFailMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The power signal of the disk is abnormal. (Cleared)"
			::= { hwDiskEvent 28 }
		hwDiskRemMediaWearoutLow NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk remnant media wearout is lower than the threshold. (Generated)"
			::= { hwDiskEvent 29 }
		hwDiskRemMediaWearoutLowDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk remnant media wearout is lower than the threshold. (Cleared)"
			::= { hwDiskEvent 30 }
		hwDiskCEHardFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk health status degradation detected by PFAE. (Generated)"
			::= { hwDiskEvent 31 }
		hwDiskCEHardFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk health status degradation detected by PFAE. (Cleared)"
			::= { hwDiskEvent 32 }
		hwDiskAccessVPDInfoFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the VPD infomation of disk. (Generated)"
			::= { hwDiskEvent 33 }
		hwDiskAccessVPDInfoFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the VPD infomation of disk. (Cleared)"
			::= { hwDiskEvent 34 }
		hwDiskReplaced NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Disk is replaced."
			::= { hwDiskEvent 35 }
		hwDiskLinkFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk link is faulty. (Generated)"
			::= { hwDiskEvent 37 }
		hwDiskLinkFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk link is faulty. (Cleared)"
			::= { hwDiskEvent 38 }
		hwDiskStateAbnormal NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk state is abnormal. (Generated)"
			::= { hwDiskEvent 39 }
		hwDiskStateAbnormalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk state is abnormal. (Cleared)"
			::= { hwDiskEvent 40 }
		hwDiskStateForeign NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk has foreign configuration. (Generated)"
			::= { hwDiskEvent 41 }
		hwDiskStateForeignDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk has foreign configuration. (Cleared)"
			::= { hwDiskEvent 42 }
		hwDiskLocateError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk link is abnormal. (Generated)"
			::= { hwDiskEvent 43 }
		hwDiskLocateErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk link is abnormal. (Cleared)"
			::= { hwDiskEvent 44 }
		hwDiskMissing NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk is missing. (Generated)"
			::= { hwDiskEvent 45 }
		hwDiskMissingDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk is missing. (Cleared)"
			::= { hwDiskEvent 46 }
		hwDiskToRAIDLinkPHYFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PHY bit errors of the link between disk and RAID card increased too fast. (Generated)"
			::= { hwDiskEvent 47 }
		hwDiskToRAIDLinkPHYFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PHY bit errors of the link between disk and RAID card increased too fast. (Cleared)"
			::= { hwDiskEvent 48 }
		hwDiskToExpanderLinkPHYFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PHY bit errors of the link between disk and expander increased too fast. (Generated)"
			::= { hwDiskEvent 49 }
		hwDiskToExpanderLinkPHYFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PHY bit errors of the link between disk and expander increased too fast. (Cleared)"
			::= { hwDiskEvent 50 }
		hwDiskTemporarilyDisconnection NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The disk disconnected temporarily. (Generated)"
			::= { hwDiskEvent 51 }
	hwPSUEvent OBJECT IDENTIFIER ::= {hwServerTRAPObjectV2 4 }
		hwPSUInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PSU installed."
			::= { hwPSUEvent 3 }
		hwPSURemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PSU removed."
			::= { hwPSUEvent 5 }
		hwPSURedundancyLost NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power supply redundancy lost. (Generated)"
			::= { hwPSUEvent 7 }
		hwPSURedundancyLostDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power supply redundancy lost. (Cleared)"
			::= { hwPSUEvent 8 }
		hwPSUFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PSU fault. (Generated)"
			::= { hwPSUEvent 9 }
		hwPSUFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PSU fault. (Cleared)"
			::= { hwPSUEvent 10 }
		hwPSUPredictiveFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PSU predictive fault. (Generated)"
			::= { hwPSUEvent 11 }
		hwPSUPredictiveFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PSU predictive fault. (Cleared)"
			::= { hwPSUEvent 12 }
		hwPSUInputLost NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Input power lost. (Generated)"
			::= { hwPSUEvent 13 }
		hwPSUInputLostDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Input power lost. (Cleared)"
			::= { hwPSUEvent 14 }
		hwPSUFanFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PSU fan fault. (Generated)"
			::= { hwPSUEvent 15 }
		hwPSUFanFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PSU fan fault. (Cleared)"
			::= { hwPSUEvent 16 }
		hwPSUOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PSU overheating. (Generated)"
			::= { hwPSUEvent 17 }
		hwPSUOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PSU overheating. (Cleared)"
			::= { hwPSUEvent 18 }
		hwPSUCommunicationFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Communication with PSU failed. (Generated)"
			::= { hwPSUEvent 19 }
		hwPSUCommunicationFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Communication with PSU failed. (Cleared)"
			::= { hwPSUEvent 20 }
		hwPSUOutputOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Output power overvoltage. (Generated)"
			::= { hwPSUEvent 21 }
		hwPSUOutputOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Output power overvoltage. (Cleared)"
			::= { hwPSUEvent 22 }
		hwPSUOutputLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Output power undervoltage or no output. (Generated)"
			::= { hwPSUEvent 23 }
		hwPSUOutputLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Output power undervoltage or no output. (Cleared)"
			::= { hwPSUEvent 24 }
		hwPSUOutputOverCurrent NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Output power overcurrent. (Generated)"
			::= { hwPSUEvent 25 }
		hwPSUOutputOverCurrentDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Output power overcurrent. (Cleared)"
			::= { hwPSUEvent 26 }
		hwPSUInputOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Input power overvoltage. (Generated)"
			::= { hwPSUEvent 27 }
		hwPSUInputOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Input power overvoltage. (Cleared)"
			::= { hwPSUEvent 28 }
		hwPSUServerPowerFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Server power failure."
			::= { hwPSUEvent 31 }	
		hwPSUDetectFail NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to identify PSU.(Generated)"
			::= { hwPSUEvent 47 }	
		hwPSUDetectFailDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to identify PSU.(Cleared)"
			::= { hwPSUEvent 48 }
	hwFanEvent OBJECT IDENTIFIER ::= {hwServerTRAPObjectV2 5 }
		hwFanInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fan installed."
			::= { hwFanEvent 1 }
		hwFanRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fan removed."
			::= { hwFanEvent 3 }
		hwFanRedundancy NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fan redundancy lost. (Generated)"
			::= { hwFanEvent 5 }
		hwFanRedundancyDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fan redundancy lost. (Cleared)"
			::= { hwFanEvent 6 }
		hwFanSpeedDeviation NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Large fan speed deviation. (Generated)"
			::= { hwFanEvent 7 }
		hwFanSpeedDeviationDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Large fan speed deviation. (Cleared)"
			::= { hwFanEvent 8 }
	hwDiskBackplaneEvent OBJECT IDENTIFIER ::= {hwServerTRAPObjectV2 6 }
		hwDiskBackplanePSFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk backplane power failure. (Generated)"
			::= { hwDiskBackplaneEvent 1 }
		hwDiskBackplanePSFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk backplane power failure. (Cleared)"
			::= { hwDiskBackplaneEvent 2 }
		hwDiskBackplaneCPLDSelfTestFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk backplane CPLD self-test failed. (Generated)"
			::= { hwDiskBackplaneEvent 3 }
		hwDiskBackplaneCPLDSelfTestFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk backplane CPLD self-test failed. (Cleared)"
			::= { hwDiskBackplaneEvent 4 }
		hwDiskBackplaneLowerVoltMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk backplane undervoltage major alarm. (Generated)"
			::= { hwDiskBackplaneEvent 5 }
		hwDiskBackplaneLowerVoltMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk backplane undervoltage major alarm. (Cleared)"
			::= { hwDiskBackplaneEvent 6 }
		hwDiskBackplaneOverVoltMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk backplane overvoltage major alarm. (Generated)"
			::= { hwDiskBackplaneEvent 7 }
		hwDiskBackplaneOverVoltMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk backplane overvoltage major alarm. (Cleared)"
			::= { hwDiskBackplaneEvent 8 }
		hwDiskBackplaneAccessVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read hard disk backplane voltage. (Generated)"
			::= { hwDiskBackplaneEvent 9 }
		hwDiskBackplaneAccessVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read hard disk backplane voltage. (Cleared)"
			::= { hwDiskBackplaneEvent 10 }
		hwDiskBackplanePowerFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power supply to disk backplane failed. (Generated)"
			::= { hwDiskBackplaneEvent 11 }
		hwDiskBackplanePowerFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power supply to disk backplane failed. (Cleared)"
			::= { hwDiskBackplaneEvent 12 }
		hwDiskBackplaneAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain data of the disk backplane temperature detection point temperature. (Generated)"
			::= { hwDiskBackplaneEvent 13 }
		hwDiskBackplaneAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain data of the disk backplane temperature detection point temperature. (Cleared)"
			::= { hwDiskBackplaneEvent 14 }
		hwDiskBackplaneClockSignalLost NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Disk backplane clock signals lost. (Generated)"
			::= { hwDiskBackplaneEvent 17 }
		hwDiskBackplaneClockSignalLostDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Disk backplane clock signals lost. (Cleared)"
			::= { hwDiskBackplaneEvent 18 }	
	hwRAIDCardEvent OBJECT IDENTIFIER ::= {hwServerTRAPObjectV2 7 }
		hwRAIDCardInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card installed."
			::= { hwRAIDCardEvent 1 }
		hwRAIDCardRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card removed."
			::= { hwRAIDCardEvent 3 }
		hwRAIDCardFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card fault. (Generated)"
			::= { hwRAIDCardEvent 5 }
		hwRAIDCardFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card fault. (Cleared)"
			::= { hwRAIDCardEvent 6 }
		hwRAIDCardUncorrectableErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card MCE/AER error. (Generated)"
			::= { hwRAIDCardEvent 7 }
		hwRAIDCardUncorrectableErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card MCE/AER error. (Cleared)"
			::= { hwRAIDCardEvent 8 }
		hwRAIDCardOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card overheating minor alarm. (Generated)"
			::= { hwRAIDCardEvent 11 }
		hwRAIDCardOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card overheating minor alarm. (Cleared)"
			::= { hwRAIDCardEvent 12 }
		hwRAIDCardAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read RAID controller card temperature. (Generated)"
			::= { hwRAIDCardEvent 13 }
		hwRAIDCardAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read RAID controller card temperature. (Cleared)"
			::= { hwRAIDCardEvent 14 }
		hwRAIDBBULowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card BBU undervoltage. (Generated)"
			::= { hwRAIDCardEvent 15 }
		hwRAIDBBULowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card BBU undervoltage. (Cleared)"
			::= { hwRAIDCardEvent 16 }
		hwRAIDBBUFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card BBU fault. (Generated)"
			::= { hwRAIDCardEvent 17 }
		hwRAIDBBUFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card BBU fault. (Cleared)"
			::= { hwRAIDCardEvent 18 }
		hwRAIDBBUNotPresent NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card BBU not detected."
			::= { hwRAIDCardEvent 19 }
		hwRAIDBBUPresent NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card BBU detected."
			::= { hwRAIDCardEvent 21 }
        hwRAIDCardOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card overheating major alarm. (Generated)"
			::= { hwRAIDCardEvent 23 }
		hwRAIDCardOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card overheating major alarm. (Cleared)"
			::= { hwRAIDCardEvent 24 }
		hwRAIDCardBBUOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card BBU overheating minor alarm. (Generated)"
			::= { hwRAIDCardEvent 25 }
		hwRAIDCardBBUOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card BBU overheating minor alarm. (Cleared)"
			::= { hwRAIDCardEvent 26 }
		hwRAIDCardBBUAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read RAID controller card BBU temperature. (Generated)"
			::= { hwRAIDCardEvent 27 }
		hwRAIDCardBBUAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read RAID controller card BBU temperature. (Cleared)"
			::= { hwRAIDCardEvent 28 }
		hwRAIDCardCEHardFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card health status degradation detected by PFAE. (Generated)"
			::= { hwRAIDCardEvent 35 }
		hwRAIDCardCEHardFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"RAID controller card health status degradation detected by PFAE. (Cleared)"
			::= { hwRAIDCardEvent 36 }	
		hwRAIDCardCommunicationLoss NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The communication between the iBMC and RAID controller card is faulty. (Generated)"
			::= { hwRAIDCardEvent 37 }
		hwRAIDCardCommunicationLossDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The communication between the iBMC and RAID controller card is faulty. (Cleared)"
			::= { hwRAIDCardEvent 38 }	
		hwRAIDCardInitializationAbnormal NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The initialization of RAID controller card is abnormal. (Generated)"
			::= { hwRAIDCardEvent 39 }
		hwRAIDCardInitializationAbnormalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The initialization of RAID controller card is abnormal. (Cleared)"
			::= { hwRAIDCardEvent 40 }				
	hwPCIeCardEvent OBJECT IDENTIFIER ::= {hwServerTRAPObjectV2 9 }
		hwPCIeCardUncorrectableErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card MCE/AER error. (Generated)"
			::= { hwPCIeCardEvent 1 }
		hwPCIeCardUncorrectableErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card MCE/AER error. (Cleared)"
			::= { hwPCIeCardEvent 2 }
		hwPCIeCardOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card overheating minor alarm. (Generated)"
			::= { hwPCIeCardEvent 3 }
		hwPCIeCardOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card overheating minor alarm. (Cleared)"
			::= { hwPCIeCardEvent 4 }
		hwPCIeCardAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe card temperature. (Generated)"
			::= { hwPCIeCardEvent 5 }
		hwPCIeCardAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe card temperature. (Cleared)"
			::= { hwPCIeCardEvent 6 }
		hwPCIeCardAccessFRULableFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe card FRU data. (Generated)"
			::= { hwPCIeCardEvent 7 }
		hwPCIeCardAccessFRULableFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe card FRU data. (Cleared)"
			::= { hwPCIeCardEvent 8 }
		hwPCIeCardDIMMOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card DIMM overheating. (Generated)"
			::= { hwPCIeCardEvent 9 }
		hwPCIeCardDIMMOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card DIMM overheating. (Cleared)"
			::= { hwPCIeCardEvent 10 }
		hwPCIeCardOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card overheating major alarm. (Generated)"
			::= { hwPCIeCardEvent 11 }
		hwPCIeCardOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card overheating major alarm. (Cleared)"
			::= { hwPCIeCardEvent 12 }
		hwPCIeCardCPUOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card CPU overheating minor alarm. (Generated)"
			::= { hwPCIeCardEvent 13 }
		hwPCIeCardCPUOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card CPU overheating minor alarm. (Cleared)"
			::= { hwPCIeCardEvent 14 }
		hwPCIeCardCPUOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card CPU overheating major alarm. (Generated)"
			::= { hwPCIeCardEvent 15 }
		hwPCIeCardCPUOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card CPU overheating major alarm. (Cleared)"
			::= { hwPCIeCardEvent 16 }
		hwPCIeCardBattLowerVoltMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card battery undervoltage minor alarm. (Generated)"
			::= { hwPCIeCardEvent 17 }
		hwPCIeCardBattLowerVoltMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card battery undervoltage minor alarm. (Cleared)"
			::= { hwPCIeCardEvent 18 }
		hwPCIeCardLowerVoltMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card undervoltage major alarm. (Generated)"
			::= { hwPCIeCardEvent 19 }
		hwPCIeCardLowerVoltMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card undervoltage major alarm. (Cleared)"
			::= { hwPCIeCardEvent 20 }
		hwPCIeCardOverVoltMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card overvoltage major alarm. (Generated)"
			::= { hwPCIeCardEvent 21 }
		hwPCIeCardOverVoltMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card overvoltage major alarm. (Cleared)"
			::= { hwPCIeCardEvent 22 }
		hwPCIeCardAccessVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe card voltage. (Generated)"
			::= { hwPCIeCardEvent 23 }
		hwPCIeCardAccessVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe card voltage. (Cleared)"
			::= { hwPCIeCardEvent 24 }
		hwPCIeCardBootEvent NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card system startup status. (Generated)"
			::= { hwPCIeCardEvent 25 }
		hwPCIeCardBootEventDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card system startup status. (Cleared)"
			::= { hwPCIeCardEvent 26 }
		hwPCIeCardHardwareFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card hardware fault. (Generated)"
			::= { hwPCIeCardEvent 27 }
		hwPCIeCardHardwareFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card hardware fault. (Cleared)"
			::= { hwPCIeCardEvent 28 }
		hwPCIeCardBootDiskAbsent NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card boot disk not detected. (Generated)"
			::= { hwPCIeCardEvent 29 }
		hwPCIeCardBootDiskAbsentDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card boot disk not detected. (Cleared)"
			::= { hwPCIeCardEvent 30 }
		hwPCIeCardDIMMFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card memory fault. (Generated)"
			::= { hwPCIeCardEvent 31 }
		hwPCIeCardDIMMFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card memory fault. (Cleared)"
			::= { hwPCIeCardEvent 32 }
		hwPCIeCardFWInitFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card firmware initialization failed. (Generated)"
			::= { hwPCIeCardEvent 33 }
		hwPCIeCardFWInitFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card firmware initialization failed. (Cleared)"
			::= { hwPCIeCardEvent 34 }
		hwPCIeCardCPUInitFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card CPU initialization failed. (Generated)"
			::= { hwPCIeCardEvent 35 }
		hwPCIeCardCPUInitFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card CPU initialization failed. (Cleared)"
			::= { hwPCIeCardEvent 36 }
		hwPCIeCardWatchDogTimeout NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card watchdog timed out. (Generated)"
			::= { hwPCIeCardEvent 37 }
		hwPCIeCardWatchDogTimeoutDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card watchdog timed out. (Cleared)"
			::= { hwPCIeCardEvent 38 }
		hwPCIeCardBBULowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card BBU undervoltage. (Generated)"
			::= { hwPCIeCardEvent 57 }
		hwPCIeCardBBULowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card BBU undervoltage. (Cleared)"
			::= { hwPCIeCardEvent 58 }
		hwPCIeCardBBUFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card BBU fault. (Generated)"
			::= { hwPCIeCardEvent 59 }
		hwPCIeCardBBUFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card BBU fault. (Cleared)"
			::= { hwPCIeCardEvent 60 }
		hwPCIeCardBBUNotPresent NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card BBU not detected."
			::= { hwPCIeCardEvent 61 }
		hwPCIeCardBBUPresent NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card BBU detected."
			::= { hwPCIeCardEvent 63 }
		hwPCIeCardPwrFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card power fault. (Generated)"
			::= { hwPCIeCardEvent 65 }
        hwPCIeCardPwrFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card power fault. (Cleared)"
			::= { hwPCIeCardEvent 66 }
		hwPCIeCardFPGALoadFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card FPGA load failure. (Generated)"
			::= { hwPCIeCardEvent 67 }
        hwPCIeCardFPGALoadFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card FPGA load failure. (Cleared)"
			::= { hwPCIeCardEvent 68 }
		hwPCIeCardEEPROMFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card EEPROM fault. (Generated)"
			::= { hwPCIeCardEvent 69 }
        hwPCIeCardEEPROMFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card EEPROM fault. (Cleared)"
			::= { hwPCIeCardEvent 70 }
		hwPCIeCardInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card installed."
			::= { hwPCIeCardEvent 71 }
		hwPCIeCardRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card removed."
			::= { hwPCIeCardEvent 73 }
		hwPCIeRAIDCardFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe RAID card fault. (Generated)"
			::= { hwPCIeCardEvent 75 }
		hwPCIeRAIDCardFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe RAID card fault. (Cleared)"
			::= { hwPCIeCardEvent 76 }
		hwPCIeCardPlugIn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card pluged in. (Generated)"
			::= { hwPCIeCardEvent 77 }
		hwPCIeCardPlugInDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card pluged in. (Cleared)"
			::= { hwPCIeCardEvent 78 }
		hwPCIeCardPlugOut NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card pluged out. (Generated)"
			::= { hwPCIeCardEvent 79 }
		hwPCIeCardPlugOutDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card pluged out. (Cleared)"
			::= { hwPCIeCardEvent 80 }
		hwPCIEClockLockLost NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The clock is out of lock. (Generated)"
			::= { hwPCIeCardEvent 81 }
		hwPCIEClockLockLostDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The clock is out of lock. (Cleared)"
			::= { hwPCIeCardEvent 82 }
		hwPCIEDDRCalibrationFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The DDR calibration failed. (Generated)"
			::= { hwPCIeCardEvent 83 }
		hwPCIEDDRCalibrationFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The DDR calibration failed. (Cleared)"
			::= { hwPCIeCardEvent 84 }
		hwPCIEDDRWorkAbnormal NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The DDR on PCIe card is malfunctioning. (Generated)"
			::= { hwPCIeCardEvent 85 }
		hwPCIEDDRWorkAbnormalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The DDR on PCIe card is malfunctioning. (Cleared)"
			::= { hwPCIeCardEvent 86 }
		hwPCIELinkAbnormal NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The link on PCIe card is faulty. (Generated)"
			::= { hwPCIeCardEvent 87 }
		hwPCIELinkAbnormalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The link on PCIe card is faulty. (Cleared)"
			::= { hwPCIeCardEvent 88 }
		hwPCIEBusinessAbnormal NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Services on PCIe card are interrupted. (Generated)"
			::= { hwPCIeCardEvent 89 }
		hwPCIEBusinessAbnormalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Services on PCIe card are interrupted. (Cleared)"
			::= { hwPCIeCardEvent 90 }
		hwPCIESelfTestFail NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card self-test failed. (Generated)"
			::= { hwPCIeCardEvent 93 }
		hwPCIESelfTestFailDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card self-test failed. (Cleared)"
			::= { hwPCIeCardEvent 94 }
		hwPCIERecovError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Recoverable errors are detected on PCIe card. (Generated)"
			::= { hwPCIeCardEvent 95 }
		hwPCIERecovErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Recoverable errors are detected on PCIe card. (Cleared)"
			::= { hwPCIeCardEvent 96 }
		hwPCIeCardOMOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card optical module overheating minor alarm. (Generated)"
			::= { hwPCIeCardEvent 99 }
		hwPCIeCardOMOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card optical module overheating minor alarm. (Cleared)"
			::= { hwPCIeCardEvent 100 }
		hwPCIeCardCEHardFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card health status degradation detected by PFAE. (Generated)"
			::= { hwPCIeCardEvent 101 }
		hwPCIeCardCEHardFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card health status degradation detected by PFAE.  (Cleared)"
			::= { hwPCIeCardEvent 102 }
		hwPCIeCardEnumerationFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Enumeration of the PCIe device failed. (Generated)"
			::= { hwPCIeCardEvent 103 }
		hwPCIeCardEnumerationFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Enumeration of the PCIe device failed. (Cleared)"
			::= { hwPCIeCardEvent 104 }
		hwPCIeCardInspectionFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PCIe card inspection failed. (Generated)"
			::= { hwPCIeCardEvent 105 }
		hwPCIeCardInspectionFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PCIe card inspection failed. (Cleared)"
			::= { hwPCIeCardEvent 106 }     
        hwPCIeCardAccessDIMMTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the DIMM temperature of PCIe card. (Generated)"
			::= { hwPCIeCardEvent 107 }
		hwPCIeCardAccessDIMMTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the DIMM temperature of PCIe card. (Cleared)"
			::= { hwPCIeCardEvent 108 }
		hwPCIeCardMemoryFaultCount NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card memory fault count exceeds the threshold. (Generated)"
			::= { hwPCIeCardEvent 109 }
		hwPCIeCardMemoryFaultCountDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card memory fault count exceeds the threshold. (Cleared)"
			::= { hwPCIeCardEvent 110 }
		hwPCIeCardBandWidthDecreased NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card bandwidth decreased. (Generated)"
			::= { hwPCIeCardEvent 111 }
		hwPCIeCardBandWidthDecreasedDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card bandwidth decreased. (Cleared)"
			::= { hwPCIeCardEvent 112 }
        hwPCIeCardComponentAbsentNormal NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The component of PCIe card is absent."
			::= { hwPCIeCardEvent 113 }
        hwPCIeCardComponentAbsentMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The component of PCIe card is absent. (Generated)"
			::= { hwPCIeCardEvent 115 }
        hwPCIeCardComponentAbsentMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The component of PCIe card is absent. (Cleared)"
			::= { hwPCIeCardEvent 116 }
		hwPCIeCardAccessHardInfoFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the PCIe card hardware information. (Generated)"
			::= { hwPCIeCardEvent 117 }
		hwPCIeCardAccessHardInfoFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the PCIe card hardware information. (Cleared)"
			::= { hwPCIeCardEvent 118 }
		hwPCIeCardAccessPowerFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the PCIe card power. (Generated)"
			::= { hwPCIeCardEvent 119 }
		hwPCIeCardAccessPowerFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the PCIe card power. (Cleared)"
			::= { hwPCIeCardEvent 120 }
		hwPCIeCardHighVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card voltage is too high. (Generated)"
			::= { hwPCIeCardEvent 123 }
		hwPCIeCardHighVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card voltage is too high. (Cleared)"
			::= { hwPCIeCardEvent 124 }
		hwPCIeCardLowVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card voltage is too low. (Generated)"
			::= { hwPCIeCardEvent 125 }
		hwPCIeCardLowVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card voltage is too low. (Cleared)"
			::= { hwPCIeCardEvent 126 }
		hwPCIeCardOverCurrentProtection NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card current exceeds the protection point. (Generated)"
			::= { hwPCIeCardEvent 129 }
		hwPCIeCardOverCurrentProtectionDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card current exceeds the protection point. (Cleared)"
			::= { hwPCIeCardEvent 130 }
		hwPCIeCardOverTempProtection NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card temperature exceeds the protection point. (Generated)"
			::= { hwPCIeCardEvent 131 }
		hwPCIeCardOverTempProtectionDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card temperature exceeds the protection point. (Cleared)"
			::= { hwPCIeCardEvent 132 }			
		hwPCIeCardSwitchModuleFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PCIe switch of the PCIe card is faulty. (Generated)"
			::= { hwPCIeCardEvent 133 }				
		hwPCIeCardSwitchModuleFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PCIe switch of the PCIe card is faulty. (Cleared)"
			::= { hwPCIeCardEvent 134 }			
		hwPCIeCardMiniModuleFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The MINI module of the PCIe card  is faulty. (Generated)"
			::= { hwPCIeCardEvent 135 }
		hwPCIeCardMiniModuleFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The MINI module of the PCIe card  is faulty. (Cleared)"
			::= { hwPCIeCardEvent 136 }			
		hwPCIeCardGetMiniModuleHealthFail NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the health status of the PCIe card  MINI module. (Generated)"
			::= { hwPCIeCardEvent 137 }
		hwPCIeCardGetMiniModuleHealthFailDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the health status of the PCIe card  MINI module. (Cleared)"
			::= { hwPCIeCardEvent 138 }			
		hwPCIeCardUnderclocking NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PCIe card underclocking. (Generated)"
			::= { hwPCIeCardEvent 139 }
		hwPCIeCardUnderclockingDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PCIe card underclocking. (Cleared)"
			::= { hwPCIeCardEvent 140 }			
		hwPCIeCardPowerOff NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PCIe card was powered off. (Generated)"
			::= { hwPCIeCardEvent 141 }
		hwPCIeCardPowerOffDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PCIe card was powered off. (Cleared)"
			::= { hwPCIeCardEvent 142 }			
		hwPCIeCardChipReset NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PCIe card chip was reset.  (Generated)"
			::= { hwPCIeCardEvent 143 }	
		hwPCIeRAIDCardCommunicationLoss NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The communication between the iBMC and PCIe card is faulty. (Generated)"
			::= { hwPCIeCardEvent 149 }
		hwPCIeRAIDCardCommunicationLossDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The communication between the iBMC and PCIe card is faulty. (Cleared)"
			::= { hwPCIeCardEvent 150 }	
		hwPCIeRAIDCardInitializationAbnormal NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The initialization of the PCIe card is abnormal. (Generated)"
			::= { hwPCIeCardEvent 151 }
		hwPCIeRAIDCardInitializationAbnormalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The initialization of the PCIe card is abnormal. (Cleared)"
			::= { hwPCIeCardEvent 152 }	
	hwMezzCardEvent OBJECT IDENTIFIER ::= {hwServerTRAPObjectV2 12 }
		hwMezzCardOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card overheating minor alarm. (Generated)"
			::= { hwMezzCardEvent 1 }
		hwMezzCardOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card overheating minor alarm. (Cleared)"
			::= { hwMezzCardEvent 2 }
		hwMezzCardOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card overheating major alarm. (Generated)"
			::= { hwMezzCardEvent 3 }
		hwMezzCardOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card overheating major alarm. (Cleared)"
			::= { hwMezzCardEvent 4 }
		hwMezzCardUncorrectableErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card MCE/AER error. (Generated)"
			::= { hwMezzCardEvent 5 }
		hwMezzCardUncorrectableErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card MCE/AER error. (Cleared)"
			::= { hwMezzCardEvent 6 }
		hwMezzCardAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card temperature. (Generated)"
			::= { hwMezzCardEvent 7 }
		hwMezzCardAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card temperature. (Cleared)"
			::= { hwMezzCardEvent 8 }
		hwMezzCardAccessFRULableFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card electronic label. (Generated)"
			::= { hwMezzCardEvent 9 }
		hwMezzCardAccessFRULableFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card electronic label. (Cleared)"
			::= { hwMezzCardEvent 10 }
		hwMezzCardOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card overvoltage major alarm. (Generated)"
			::= { hwMezzCardEvent 11 }
		hwMezzCardOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card overvoltage major alarm. (Cleared)"
			::= { hwMezzCardEvent 12 }
		hwMezzCardLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card undervoltage major alarm. (Generated)"
			::= { hwMezzCardEvent 13 }
		hwMezzCardLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card undervoltage major alarm. (Cleared)"
			::= { hwMezzCardEvent 14 }
		hwMezzCardSVIDChipFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card failed to obtain WFR chip SVID. (Generated)"
			::= { hwMezzCardEvent 31 }
		hwMezzCardSVIDChipFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card failed to obtain WFR chip SVID. (Cleared)"
			::= { hwMezzCardEvent 32 }
		hwMezzCardVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card voltage. (Generated)"
			::= { hwMezzCardEvent 33 }
		hwMezzCardVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card voltage. (Cleared)"
			::= { hwMezzCardEvent 34 }
		hwMezzCardCEHardFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card health status degradation detected by PFAE. (Generated)"
			::= { hwMezzCardEvent 35 }
		hwMezzCardCEHardFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card health status degradation detected by PFAE. (Cleared)"
			::= { hwMezzCardEvent 36 }
		hwMezzCardNotInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The mezzanine card is not installed. "
			::= { hwMezzCardEvent 37 }
	hwNetworkCardEvent OBJECT IDENTIFIER ::= {hwServerTRAPObjectV2 14 }
		hwNetworkCardUncorrectableErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The NIC triggered an uncorrectable error.(Generated)"
			::= { hwNetworkCardEvent 1 }
		hwNetworkCardUncorrectableErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The NIC triggered an uncorrectable error.( Cleared)"
			::= { hwNetworkCardEvent 2 }
		hwNetworkCardOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NIC overheating minor alarm. (Generated)"
			::= { hwNetworkCardEvent 3 }
		hwNetworkCardOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NIC overheating minor alarm. (Cleared)"
			::= { hwNetworkCardEvent 4 }
		hwNetworkCardAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read NIC temperature. (Generated)"
			::= { hwNetworkCardEvent 5 }
		hwNetworkCardAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read NIC temperature. (Cleared)"
			::= { hwNetworkCardEvent 6 }
		hwNetworkCardCEHardFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NIC health status degradation detected by PFAE. (Generated)"
			::= { hwNetworkCardEvent 7 }
		hwNetworkCardCEHardFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NIC health status degradation detected by PFAE. (Cleared)"
			::= { hwNetworkCardEvent 8 }	
	hwMemoryBoardEvent OBJECT IDENTIFIER ::= {hwServerTRAPObjectV2 15 }
		hwMemoryBoardLowerTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory board undertemperature. (Generated)"
			::= { hwMemoryBoardEvent 1 }
		hwMemoryBoardLowerTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory board undertemperature. (Cleared)"
			::= { hwMemoryBoardEvent 2 }
		hwMemoryBoardAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read memory board temperature. (Generated)"
			::= { hwMemoryBoardEvent 3 }
		hwMemoryBoardAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read memory board temperature. (Cleared)"
			::= { hwMemoryBoardEvent 4 }
		hwMemoryBoardSMI2TainingError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Initialization error on SMI2 link of memory board. (Generated)"
			::= { hwMemoryBoardEvent 5 }
		hwMemoryBoardSMI2TainingErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Initialization error on SMI2 link of memory board. (Cleared)"
			::= { hwMemoryBoardEvent 6 }
	hwPCIeRiserEvent OBJECT IDENTIFIER ::= {hwServerTRAPObjectV2 16 }
		hwPCIeRiserInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe riser card installed."
			::= { hwPCIeRiserEvent 1 }
		hwPCIeRiserRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe riser card removed."
			::= { hwPCIeRiserEvent 3 }
		hwPCIeRiserOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe riser card temperature exceeds the overtemperature threshold.(Generated)"
			::= { hwPCIeRiserEvent 5 }
		hwPCIeRiserOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe riser card temperature exceeds the overtemperature threshold.(Cleared)"
			::= { hwPCIeRiserEvent 6 }
		hwPCIeRiserAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain data of the PCIe riser card temperature.(Generated)"
			::= { hwPCIeRiserEvent 7 }
		hwPCIeRiserAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain data of the PCIe riser card temperature.(Cleared)"
			::= { hwPCIeRiserEvent 8 }
		hwPCIeRiserlowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe riser voltage at detection point is lower than the undervoltage threshold.(Generated)"
			::= { hwPCIeRiserEvent 9 }
		hwPCIeRiserlowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe riser voltage at detection point is lower than the undervoltage threshold.(Cleared)"
			::= { hwPCIeRiserEvent 10 }
		hwPCIeRiserOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe riser voltage at detection point exceeds the overvoltage threshold.(Generated)"
			::= { hwPCIeRiserEvent 11 }
		hwPCIeRiserOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe riser voltage at detection point exceeds the overvoltage threshold.(Cleared)"
			::= { hwPCIeRiserEvent 12 }
		hwPCIeRiserAccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the voltage at detection point on the PCIe riser.(Generated)"
			::= { hwPCIeRiserEvent 13 }
		hwPCIeRiserAccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the voltage at detection point on the PCIe riser.(Cleared)"
			::= { hwPCIeRiserEvent 14 }
		hwPCIeRiserOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Pebpa backplane power supply over temperature.(Generated)"
			::= { hwPCIeRiserEvent 15 }
		hwPCIeRiserOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Pebpa backplane power supply over temperature.(Cleared)"
			::= { hwPCIeRiserEvent 16 }
		hwPCIeRiserPowerFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe riser card power failure.(Generated)"
			::= { hwPCIeRiserEvent 17 }
		hwPCIeRiserPowerFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe riser card power failure.(Cleared)"
			::= { hwPCIeRiserEvent 18 }	
	hwMainboardEvent OBJECT IDENTIFIER ::= {hwServerTRAPObjectV2 17 }
		hwMainboard3V3LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 3.3V undervoltage major alarm. (Generated)"
			::= { hwMainboardEvent 1 }
		hwMainboard3V3LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 3.3V undervoltage major alarm. (Cleared)"
			::= { hwMainboardEvent 2 }
		hwMainboard3V3OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 3.3V overvoltage major alarm. (Generated)"
			::= { hwMainboardEvent 3 }
		hwMainboard3V3OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 3.3V overvoltage major alarm. (Cleared)"
			::= { hwMainboardEvent 4 }
		hwMainboard5VLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 5V undervoltage major alarm. (Generated)"
			::= { hwMainboardEvent 5 }
		hwMainboard5VLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 5V undervoltage major alarm. (Cleared)"
			::= { hwMainboardEvent 6 }
		hwMainboard5VOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 5V overvoltage major alarm. (Generated)"
			::= { hwMainboardEvent 7 }
		hwMainboard5VOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 5V overvoltage major alarm. (Cleared)"
			::= { hwMainboardEvent 8 }
		hwMainboard12VLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 12V undervoltage major alarm. (Generated)"
			::= { hwMainboardEvent 9 }
		hwMainboard12VLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 12V undervoltage major alarm. (Cleared)"
			::= { hwMainboardEvent 10 }
		hwMainboard12VOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 12V overvoltage major alarm. (Generated)"
			::= { hwMainboardEvent 11 }
		hwMainboard12VOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 12V overvoltage major alarm. (Cleared)"
			::= { hwMainboardEvent 12 }
		hwMainboardRTCLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard RTC battery undervoltage. (Generated)"
			::= { hwMainboardEvent 13 }
		hwMainboardRTCLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard RTC battery undervoltage. (Cleared)"
			::= { hwMainboardEvent 14 }
		hwMainboardStdby3V3LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 3.3V undervoltage major alarm. (Generated)"
			::= { hwMainboardEvent 15 }
		hwMainboardStdby3V3LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 3.3V undervoltage major alarm. (Cleared)"
			::= { hwMainboardEvent 16 }
		hwMainboardStdby3V3OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 3.3V overvoltage major alarm. (Generated)"
			::= { hwMainboardEvent 17 }
		hwMainboardStdby3V3OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 3.3V overvoltage major alarm. (Cleared)"
			::= { hwMainboardEvent 18 }
		hwMainboardIncorrectHWAddr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect hardware address of board. (Generated)"
			::= { hwMainboardEvent 19 }
		hwMainboardIncorrectHWAddrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect hardware address of board. (Cleared)"
			::= { hwMainboardEvent 20 }
		hwMainboardCPLDSelfTestFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard CPLD self-test status. (Generated)"
			::= { hwMainboardEvent 21 }
		hwMainboardCPLDSelfTestFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard CPLD self-test status. (Cleared)"
			::= { hwMainboardEvent 22 }
		hwMainboardPSFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard power supply failure. (Generated)"
			::= { hwMainboardEvent 23 }
		hwMainboardPSFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard power supply failure. (Cleared)"
			::= { hwMainboardEvent 24 }
		hwMainboardAccessSlotFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect slot number. (Generated)"
			::= { hwMainboardEvent 25 }
		hwMainboardAccessSlotFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect slot number. (Cleared)"
			::= { hwMainboardEvent 26 }
		hwMainboardNotProperlyInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Board not securely installed. (Generated)"
			::= { hwMainboardEvent 27 }
		hwMainboardNotProperlyInstalledDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Board not securely installed. (Cleared)"
			::= { hwMainboardEvent 28 }
		hwMainboardAccessBoardIDFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect board ID. (Generated)"
			::= { hwMainboardEvent 29 }
		hwMainboardAccessBoardIDFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect board ID. (Cleared)"
			::= { hwMainboardEvent 30 }
		hwMainboardStdby1VLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard standby 1V undervoltage major alarm. (Generated)"
			::= { hwMainboardEvent 31 }
		hwMainboardStdby1VLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard standby 1V undervoltage major alarm. (Cleared)"
			::= { hwMainboardEvent 32 }
		hwMainboardStdby1VOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard standby 1V overvoltage major alarm. (Generated)"
			::= { hwMainboardEvent 33 }
		hwMainboardStdby1VOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard standby 1V overvoltage major alarm. (Cleared)"
			::= { hwMainboardEvent 34 }
		hwMainboardStdby2V5LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard standby 2.5V undervoltage major alarm. (Generated)"
			::= { hwMainboardEvent 35 }
		hwMainboardStdby2V5LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard standby 2.5V undervoltage major alarm. (Cleared)"
			::= { hwMainboardEvent 36 }
		hwMainboardStdby2V5OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard standby 2.5V overvoltage major alarm. (Generated)"
			::= { hwMainboardEvent 37 }
		hwMainboardStdby2V5OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard standby 2.5V overvoltage major alarm. (Cleared)"
			::= { hwMainboardEvent 38 }
		hwMainboard1VLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard 1V undervoltage major alarm. (Generated)"
			::= { hwMainboardEvent 39 }
		hwMainboard1VLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard 1V undervoltage major alarm. (Cleared)"
			::= { hwMainboardEvent 40 }
		hwMainboard1VOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard 1V overvoltage major alarm. (Generated)"
			::= { hwMainboardEvent 41 }
		hwMainboard1VOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard 1V overvoltage major alarm. (Cleared)"
			::= { hwMainboardEvent 42 }
		hwMainboard1V5LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard 1.5V undervoltage major alarm. (Generated)"
			::= { hwMainboardEvent 43 }
		hwMainboard1V5LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard 1.5V undervoltage major alarm. (Cleared)"
			::= { hwMainboardEvent 44 }
		hwMainboard1V5OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard 1.5V overvoltage major alarm. (Generated)"
			::= { hwMainboardEvent 45 }
		hwMainboard1V5OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard 1.5V overvoltage major alarm. (Cleared)"
			::= { hwMainboardEvent 46 }
		hwMainboardMOSOverVoltageMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Large voltage difference on mainboard MOSFET (major alarm). (Generated)"
			::= { hwMainboardEvent 47 }
		hwMainboardMOSOverVoltageMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Large voltage difference on mainboard MOSFET (major alarm). (Cleared)"
			::= { hwMainboardEvent 48 }
		hwMainboardMOSOverVoltageCritical NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Large voltage difference on mainboard MOSFET (critical alarm). (Generated)"
			::= { hwMainboardEvent 49 }
		hwMainboardMOSOverVoltageCriticalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Large voltage difference on mainboard MOSFET (critical alarm). (Cleared)"
			::= { hwMainboardEvent 50 }
		hwMainboardStdby5VLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 5V undervoltage major alarm. (Generated)"
			::= { hwMainboardEvent 51 }
		hwMainboardStdby5VLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 5V undervoltage major alarm. (Cleared)"
			::= { hwMainboardEvent 52 }
		hwMainboardStdby5VOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 5V overvoltage major alarm. (Generated)"
			::= { hwMainboardEvent 53 }
		hwMainboardStdby5VOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 5V overvoltage major alarm. (Cleared)"
			::= { hwMainboardEvent 54 }
		hwMainboard1V1LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 1.1V undervoltage major alarm. (Generated)"
			::= { hwMainboardEvent 59 }
		hwMainboard1V1LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 1.1V undervoltage major alarm. (Cleared)"
			::= { hwMainboardEvent 60 }
		hwMainboard1V1OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 1.1V overvoltage major alarm. (Generated)"
			::= { hwMainboardEvent 61 }
		hwMainboard1V1OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System 1.1V overvoltage major alarm. (Cleared)"
			::= { hwMainboardEvent 62 }
		hwMainboardStdby1V2LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard standby 1.2V undervoltage major alarm. (Generated)"
			::= { hwMainboardEvent 63 }
		hwMainboardStdby1V2LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard standby 1.2V undervoltage major alarm. (Cleared)"
			::= { hwMainboardEvent 64 }
		hwMainboardStdby1V2OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard standby 1.2V overvoltage major alarm. (Generated)"
			::= { hwMainboardEvent 65 }
		hwMainboardStdby1V2OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard standby 1.2V overvoltage major alarm. (Cleared)"
			::= { hwMainboardEvent 66 }
		hwMainboardNotInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard not installed."
			::= { hwMainboardEvent 75 }
		hwMainboardNotPowerOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard installed but powered off."
			::= { hwMainboardEvent 77 }
		hwMainboardReqPowerOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard requesting power-on."
			::= { hwMainboardEvent 79 }
		hwMainboardBeingPowerOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard in power-on process."
			::= { hwMainboardEvent 81 }
		hwMainboardPoweredOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard powered on."
			::= { hwMainboardEvent 83 }
		hwMainboardReqPowerOff NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard requesting power-off."
			::= { hwMainboardEvent 85 }
		hwMainboardBeingPowerOff NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard in power-off process."
			::= { hwMainboardEvent 87 }
		hwMainboardAndManageBoardCommLost NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard-MM communication interrupted. (Generated)"
			::= { hwMainboardEvent 89 }
		hwMainboardAndManageBoardCommLostDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard-MM communication interrupted. (Cleared)"
			::= { hwMainboardEvent 90 }
		hwMainboardMOSOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Soft-start circuit overheating minor alarm. (Generated)"
			::= { hwMainboardEvent 91 }
		hwMainboardMOSOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Soft-start circuit overheating minor alarm. (Cleared)"
			::= { hwMainboardEvent 92 }
		hwMainboardSoftStartPGAbnormal NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Soft-start circuit power supply abnormal. (Generated)"
			::= { hwMainboardEvent 93 }
		hwMainboardSoftStartPGAbnormalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Soft-start circuit power supply abnormal. (Cleared)"
			::= { hwMainboardEvent 94 }
		hwMainboardSoftStartFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Critical fault on soft-start circuit. (Generated)"
			::= { hwMainboardEvent 95 }
		hwMainboardSoftStartFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Critical fault on soft-start circuit. (Cleared)"
			::= { hwMainboardEvent 96 }
		hwMainboardVideoControlFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Video controller fault. (Generated)"
			::= { hwMainboardEvent 97 }
		hwMainboardVideoControlFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Video controller fault. (Cleared)"
			::= { hwMainboardEvent 98 }
		hwMainboardAccess3V3Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read system 3.3V voltage. (Generated)"
			::= { hwMainboardEvent 99 }
		hwMainboardAccess3V3FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read system 3.3V voltage. (Cleared)"
			::= { hwMainboardEvent 100 }
		hwMainboardAccess5VFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read system 5V voltage. (Generated)"
			::= { hwMainboardEvent 101 }
		hwMainboardAccess5VFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read system 5V voltage. (Cleared)"
			::= { hwMainboardEvent 102 }
		hwMainboardAccess12VFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read system 12V voltage. (Generated)"
			::= { hwMainboardEvent 103 }
		hwMainboardAccess12VFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read system 12V voltage. (Cleared)"
			::= { hwMainboardEvent 104 }
		hwMainboardAccess1V1Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read system 1.1V voltage. (Generated)"
			::= { hwMainboardEvent 105 }
		hwMainboardAccess1V1FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read system 1.1V voltage. (Cleared)"
			::= { hwMainboardEvent 106 }
		hwMainboardAccess1V5Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read system 1.5V voltage. (Generated)"
			::= { hwMainboardEvent 107 }
		hwMainboardAccess1V5FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read system 1.5V voltage. (Cleared)"
			::= { hwMainboardEvent 108 }
		hwMainboardAccessStdby5VFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 5V voltage. (Generated)"
			::= { hwMainboardEvent 109 }
		hwMainboardAccessStdby5VFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 5V voltage. (Cleared)"
			::= { hwMainboardEvent 110 }
		hwMainboardAccessStdby3V3Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 3.3V voltage. (Generated)"
			::= { hwMainboardEvent 111 }
		hwMainboardAccessStdby3V3FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 3.3V voltage. (Cleared)"
			::= { hwMainboardEvent 112 }
		hwMainboardAccessStdby2V5Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 2.5V voltage. (Generated)"
			::= { hwMainboardEvent 113 }
		hwMainboardAccessStdby2V5FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 2.5V voltage. (Cleared)"
			::= { hwMainboardEvent 114 }
		hwMainboardAccessStdby1V5Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 1.5V voltage. (Generated)"
			::= { hwMainboardEvent 115 }
		hwMainboardAccessStdby1V5FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 1.5V voltage. (Cleared)"
			::= { hwMainboardEvent 116 }
		hwMainboardAccessStdby1V2Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 1.2V voltage. (Generated)"
			::= { hwMainboardEvent 117 }
		hwMainboardAccessStdby1V2FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 1.2V voltage. (Cleared)"
			::= { hwMainboardEvent 118 }
		hwMainboardAccessStdby1V1Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 1.1V voltage. (Generated)"
			::= { hwMainboardEvent 119 }
		hwMainboardAccessStdby1V1FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 1.1V voltage. (Cleared)"
			::= { hwMainboardEvent 120 }
		hwMainboardAccessStdby1VFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 1V voltage. (Generated)"
			::= { hwMainboardEvent 121 }
		hwMainboardAccessStdby1VFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 1V voltage. (Cleared)"
			::= { hwMainboardEvent 122 }
		hwMainboardMOSAccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read MOSFET voltage. (Generated)"
			::= { hwMainboardEvent 123 }
		hwMainboardMOSAccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read MOSFET voltage. (Cleared)"
			::= { hwMainboardEvent 124 }
		hwMainboardAccessFRULableFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mainboard FRU data. (Generated)"
			::= { hwMainboardEvent 137 }
		hwMainboardAccessFRULableFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mainboard FRU data. (Cleared)"
			::= { hwMainboardEvent 138 }
		hwMainboardStdby1V1LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 1.1V undervoltage major alarm. (Generated)"
			::= { hwMainboardEvent 139 }
		hwMainboardStdby1V1LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 1.1V undervoltage major alarm. (Cleared)"
			::= { hwMainboardEvent 140 }
		hwMainboardStdby1V1OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 1.1V overvoltage major alarm. (Generated)"
			::= { hwMainboardEvent 141 }
		hwMainboardStdby1V1OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 1.1V overvoltage major alarm. (Cleared)"
			::= { hwMainboardEvent 142 }
		hwMainboardStdby1V5LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 1.5V undervoltage major alarm. (Generated)"
			::= { hwMainboardEvent 143 }
		hwMainboardStdby1V5LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 1.5V undervoltage major alarm. (Cleared)"
			::= { hwMainboardEvent 144 }
		hwMainboardStdby1V5OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 1.5V overvoltage major alarm. (Generated)"
			::= { hwMainboardEvent 145 }
		hwMainboardStdby1V5OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 1.5V overvoltage major alarm. (Cleared)"
			::= { hwMainboardEvent 146 }
		hwMainboardKeyboardControllerFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PS/2 or USB keyboard controller fault. (Generated)"
			::= { hwMainboardEvent 147 }
		hwMainboardKeyboardControllerFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PS/2 or USB keyboard controller fault. (Cleared)"
			::= { hwMainboardEvent 148 }
		hwMainboardSMI2TainingError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Initialization error on SMI2 link of mainboard. (Generated)"
			::= { hwMainboardEvent 155 }
		hwMainboardSMI2TainingErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Initialization error on SMI2 link of mainboard. (Cleared)"
			::= { hwMainboardEvent 156 }
		hwMainboardMOS2OverVoltageMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Large MOS2 voltage difference on mainboard (major alarm). (Generated)"
			::= { hwMainboardEvent 157 }
		hwMainboardMOS2OverVoltageMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Large MOS2 voltage difference on mainboard (major alarm). (Cleared)"
			::= { hwMainboardEvent 158 }
		hwMainboardStdby1V8LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 1.8V undervoltage major alarm. (Generated)"
			::= { hwMainboardEvent 161 }
		hwMainboardStdby1V8LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 1.8V undervoltage major alarm. (Cleared)"
			::= { hwMainboardEvent 162 }
		hwMainboardStdby1V8OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 1.8V overvoltage major alarm. (Generated)"
			::= { hwMainboardEvent 163 }
		hwMainboardStdby1V8OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Standby 1.8V overvoltage major alarm. (Cleared)"
			::= { hwMainboardEvent 164 }
		hwMainboardAccessStdby1V8Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 1.8V voltage. (Generated)"
			::= { hwMainboardEvent 165 }
		hwMainboardAccessStdby1V8FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read standby 1.8V voltage. (Cleared)"
			::= { hwMainboardEvent 166 }
		hwMainboardAccessVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the voltage. (Generated)"
			::= { hwMainboardEvent 167 }
		hwMainboardAccessVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the voltage. (Cleared)"
			::= { hwMainboardEvent 168 }
		hwMainboardClockSignalLost NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard clock signals lost. (Generated)"
			::= { hwMainboardEvent 169 }
		hwMainboardClockSignalLostDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard clock signals lost. (Cleared)"
			::= { hwMainboardEvent 170 }
		hwMainboardRemoteBMCBoard NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Master iBMC not present. (Generated)"
			::= { hwMainboardEvent 171 }
		hwMainboardRemoteBMCBoardDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Master iBMC not present. (Cleared)"
			::= { hwMainboardEvent 172 }
		hwMainboardSPIStatusError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SPI Flash switching status error. (Generated)"
			::= { hwMainboardEvent 173 }
		hwMainboardSPIStatusErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SPI Flash switching status error. (Cleared)"
			::= { hwMainboardEvent 174 }
		hwMainboardPowerLackAlertAbnormal NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Alert signal check failed. (Generated)"
			::= { hwMainboardEvent 175 }
		hwMainboardPowerLackAlertAbnormalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Alert signal check failed. (Cleared)"
			::= { hwMainboardEvent 176 }
		hwMainboardLOMUncorrectableErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"LOM MCE/AER error. (Generated)"
			::= { hwMainboardEvent 177 }
		hwMainboardLOMUncorrectableErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"LOM MCE/AER error. (Cleared)"
			::= { hwMainboardEvent 178 }
		hwMainboardSYSLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard voltage undervoltage. (Generated)"
			::= { hwMainboardEvent 179 }
		hwMainboardSYSLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard voltage undervoltage. (Cleared)"
			::= { hwMainboardEvent 180 }
		hwMainboardSYSOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard voltage overvoltage. (Generated)"
			::= { hwMainboardEvent 181 }
		hwMainboardSYSOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard voltage overvoltage. (Cleared)"
			::= { hwMainboardEvent 182 }
		hwMainboardSoftStartLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Soft-start circuit undervoltage major alarm.  (Generated)"
			::= { hwMainboardEvent 183 }
		hwMainboardSoftStartLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Soft-start circuit undervoltage major alarm.  (Cleared)"
			::= { hwMainboardEvent 184 }
		hwMainboardWOLSignalError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The WOL signal triggered by the mezzanine card is abnormal.(Generated)"
			::= { hwMainboardEvent 185 }
		hwMainboardWOLSignalErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The WOL signal triggered by the mezzanine card is abnormal.(Cleared)"
			::= { hwMainboardEvent 186 }
		hwMainboardRAIDLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard RAID chip voltage at detection point is lower than the undervoltage threshold. (Generated)"
			::= { hwMainboardEvent 187 }
		hwMainboardRAIDLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard RAID chip voltage at detection point is lower than the undervoltage threshold. (Cleared)"
			::= { hwMainboardEvent 188 }
		hwMainboardRAIDOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard RAID chip voltage at detection point is exceeds the overvoltage threshold. (Generated)"
			::= { hwMainboardEvent 189 }
		hwMainboardRAIDOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard RAID chip voltage at detection point is exceeds the overvoltage threshold. (Cleared)"
			::= { hwMainboardEvent 190 }
		hwMainboardRAIDAccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the voltage at detection point on the Mainboard RAID chip. (Generated)"
			::= { hwMainboardEvent 191 }
		hwMainboardRAIDAccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the voltage at detection point on the Mainboard RAID chip. (Cleared)"
			::= { hwMainboardEvent 192 }
		hwMainboardStartUpOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System is forcibly shut down due to high temperature of the soft-start circuit. (Generated)"
			::= { hwMainboardEvent 193 }
		hwMainboardStartUpOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System is forcibly shut down due to high temperature of the soft-start circuit. (Cleared)"
			::= { hwMainboardEvent 194 }

		hwMainboardAccessRTCTimeFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the RTC Time on the mainboard. (Generated)"
			::= { hwMainboardEvent 195 }
		hwMainboardAccessRTCTimeFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the RTC Time on the mainboard. (Cleared)"
			::= { hwMainboardEvent 196 }
		hwMainboardAccessRTCClockFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the RTC clock on the mainboard. (Generated)"
			::= { hwMainboardEvent 197 }
		hwMainboardAccessRTCClockFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the RTC clock on the mainboard. (Cleared)"
			::= { hwMainboardEvent 198 }
		hwMainboardAccess10GEPHYClockFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the 10GE_PHY clock on the mainboard. (Generated)"
			::= { hwMainboardEvent 199 }
		hwMainboardAccess10GEPHYClockFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the 10GE_PHY clock on the mainboard. (Cleared)"
			::= { hwMainboardEvent 200 }
		hwMainboardAccessI2CDeviceFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I2C device access exception. (Generated)"
			::= { hwMainboardEvent 201 }
		hwMainboardAccessI2CDeviceFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I2C device access exception. (Cleared)"
			::= { hwMainboardEvent 202 }
		hwMainboardSoftStartPGErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Soft-start circuit power supply on the mainboard abnormal. (Generated)"
			::= { hwMainboardEvent 203 }
		hwMainboardSoftStartPGErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Soft-start circuit power supply on the mainboard abnormal. (Cleared)"
			::= { hwMainboardEvent 204 }
		hwMainboardLOMCEHardFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"LOM health status degradation detected by PFAE. (Generated)"
			::= { hwMainboardEvent 205 }
		hwMainboardLOMCEHardFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"LOM health status degradation detected by PFAE. (Cleared)"
			::= { hwMainboardEvent 206 }
		hwMainboardUSBPortOverCurrent NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The USB port on the mainboard is overcurrent. (Generated)"
			::= { hwMainboardEvent 217 }
		hwMainboardUSBPortOverCurrentDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The USB port on the mainboard is overcurrent. (Cleared)"
			::= { hwMainboardEvent 218 }		
			
	hwLCDEvent OBJECT IDENTIFIER ::= {hwServerTRAPObjectV2 18 }
		hwLCDInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"LCD installed."
			::= { hwLCDEvent 1 }
		hwLCDRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"LCD removed."
			::= { hwLCDEvent 3 }
		hwLCDModuleFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"LCD fault. (Generated)"
			::= { hwLCDEvent 5 }
		hwLCDModuleFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"LCD fault. (Cleared)"
			::= { hwLCDEvent 6 }
	hwChassisEvent OBJECT IDENTIFIER ::= {hwServerTRAPObjectV2 19 }
		hwChassisInletOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Air inlet overheating minor alarm. (Generated)"
			::= { hwChassisEvent 1 }
		hwChassisInletOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Air inlet overheating minor alarm. (Cleared)"
			::= { hwChassisEvent 2 }
		hwChassisInletOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Air inlet overheating major alarm. (Generated)"
			::= { hwChassisEvent 3 }
		hwChassisInletOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Air inlet overheating major alarm. (Cleared)"
			::= { hwChassisEvent 4 }
		hwChassisCoverOpened NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Chassis cover opened."
			::= { hwChassisEvent 5 }
		hwChassisCoverClosed NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Chassis cover closed."
			::= { hwChassisEvent 7 }
		hwChassisOutletOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Air outlet overheating minor alarm. (Generated)"
			::= { hwChassisEvent 9 }
		hwChassisOutletOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Air outlet overheating minor alarm. (Cleared)"
			::= { hwChassisEvent 10 }
		hwChassisInletOverTempCritical NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Air inlet overheating critical alarm. (Generated)"
			::= { hwChassisEvent 15 }
		hwChassisInletOverTempCriticalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Air inlet overheating critical alarm. (Cleared)"
			::= { hwChassisEvent 16 }
		hwChassisInsufficientPower NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Insufficient power supply to chassis. (Generated)"
			::= { hwChassisEvent 17 }
		hwChassisInsufficientPowerDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Insufficient power supply to chassis. (Cleared)"
			::= { hwChassisEvent 18 }
		hwChassisAccessInletTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read air inlet temperature. (Generated)"
			::= { hwChassisEvent 19 }
		hwChassisAccessInletTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read air inlet temperature. (Cleared)"
			::= { hwChassisEvent 20 }
		hwChassisInletLowerTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Air inlet undertemperature major alarm. (Generated)"
			::= { hwChassisEvent 21 }
		hwChassisInletLowerTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Air inlet undertemperature major alarm. (Cleared)"
			::= { hwChassisEvent 22 }
		hwChassisAccessOutletTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read the air outlet temperature. (Generated)"
			::= { hwChassisEvent 23 }
		hwChassisAccessOutletTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read the air outlet temperature. (Cleared)"
			::= { hwChassisEvent 24 }
		hwChassisRightMountingEarNotPresent NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Right mounting ear is not present. (Generated)"
			::= { hwChassisEvent 25 }
		hwChassisRightMountingEarNotPresentDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Right mounting ear is not present. (Cleared)"
			::= { hwChassisEvent 26 }
		hwChassisDeviceTempOverShortTermSpecification NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The system operating temperature exceeds the short-term temperature range."
			::= { hwChassisEvent 27 }
		hwChassisM2ZoneTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain data of the M.2 slot zone temperature on the mainboard. (Generated)"
			::= { hwChassisEvent 29 }
		hwChassisM2ZoneTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain data of the M.2 slot zone temperature on the mainboard. (Cleared)"
			::= { hwChassisEvent 30 }
		hwChassisM2ZoneOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The temperature of the M.2 slot zone on the mainboard exceeds the overtemperature threshold. (Generated)"
			::= { hwChassisEvent 31 }
		hwChassisM2ZoneOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The temperature of the M.2 slot zone on the mainboard exceeds the overtemperature threshold. (Cleared)"
			::= { hwChassisEvent 32 }	
	hwNCBoardEvent OBJECT IDENTIFIER ::= {hwServerTRAPObjectV2 20 }
		hwNCBoardOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NCM chip overheating minor alarm. (Generated)"
			::= { hwNCBoardEvent 5 }
		hwNCBoardOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NCM chip overheating minor alarm. (Cleared)"
			::= { hwNCBoardEvent 6 }
		hwNCBoardBandwidthDegrade NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NCM chip bandwidth decreased by 50% or ECC error. (Generated)"
			::= { hwNCBoardEvent 7 }
		hwNCBoardBandwidthDegradeDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NCM chip bandwidth decreased by 50% or ECC error. (Cleared)"
			::= { hwNCBoardEvent 8 }
		hwNCBoardSEV2Fault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SEV2 fault occurred on NCM chip. (Generated)"
			::= { hwNCBoardEvent 9 }
		hwNCBoardSEV2FaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SEV2 fault occurred on NCM chip. (Cleared)"
			::= { hwNCBoardEvent 10 }
		hwNCBoardAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read NCM chip temperature. (Generated)"
			::= { hwNCBoardEvent 11 }
		hwNCBoardAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read NCM chip temperature. (Cleared)"
			::= { hwNCBoardEvent 12 }
		hwNCBoardCPLDSelfTestFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NCM CPLD self-test failed. (Generated)"
			::= { hwNCBoardEvent 13 }
		hwNCBoardCPLDSelfTestFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NCM CPLD self-test failed. (Cleared)"
			::= { hwNCBoardEvent 14 }
		hwNCBoard12VOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NCM 12V overvoltage major alarm. (Generated)"
			::= { hwNCBoardEvent 15 }
		hwNCBoard12VOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NCM 12V overvoltage major alarm. (Cleared)"
			::= { hwNCBoardEvent 16 }
		hwNCBoardAccess12VFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read NCM 12V voltage. (Generated)"
			::= { hwNCBoardEvent 19 }
		hwNCBoardAccess12VFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read NCM 12V voltage. (Cleared)"
			::= { hwNCBoardEvent 20 }
        hwNCBoardAccess12VLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NCM 12V undervoltage major alarm. (Generated)"
			::= { hwNCBoardEvent 17 }
		hwNCBoardAccess12VLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NCM 12V undervoltage major alarm. (Cleared)"
			::= { hwNCBoardEvent 18 }
        hwNCBoardConfigCDRFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to configure CDR of NC board. (Generated)"
			::= { hwNCBoardEvent 65 }
		hwNCBoardConfigCDRFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to configure CDR of NC board. (Cleared)"
			::= { hwNCBoardEvent 66 }
    hwSwitchModuleEvent OBJECT IDENTIFIER ::= {hwServerTRAPObjectV2 21 }
        hwSwitchModuleOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Switch module overvoltage major alarm. (Generated)"
			::= { hwSwitchModuleEvent 1 }
		hwSwitchModuleOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Switch module overvoltage major alarm. (Cleared)"
			::= { hwSwitchModuleEvent 2 }
        hwSwitchModuleLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Switch module voltage below lower major threshold. (Generated)"
			::= { hwSwitchModuleEvent 3 }
		hwSwitchModuleLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Switch module voltage below lower major threshold. (Cleared)"
			::= { hwSwitchModuleEvent 4 }
        hwSwitchModuleAccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Switch module voltage. (Generated)"
			::= { hwSwitchModuleEvent 5 }
		hwSwitchModuleAccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Switch module voltage. (Cleared)"
			::= { hwSwitchModuleEvent 6 }
        hwSwitchModuleClockPower NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power supplies to clock chips on the Switch module abnormal. (Generated)"
			::= { hwSwitchModuleEvent 7 }
		hwSwitchModuleClockPowerDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power supplies to clock chips on the Switch module abnormal. (Cleared)"
			::= { hwSwitchModuleEvent 8 }
        hwSwitchModuleClock NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Switch module clock chips abnormal. (Generated)"
			::= { hwSwitchModuleEvent 9 }
		hwSwitchModuleClockDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Switch module clock chips abnormal. (Cleared)"
			::= { hwSwitchModuleEvent 10 }
        hwSwitchModulePower NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Switch module power signal abnormal. (Generated)"
			::= { hwSwitchModuleEvent 11 }
		hwSwitchModulePowerDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Switch module power signal abnormal. (Cleared)"
			::= { hwSwitchModuleEvent 12 }
	hwHMMEvent OBJECT IDENTIFIER ::= {hwServerTRAPObjectV2 24 }
		hwHMMAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain data of the HMM temperature. (Generated)"
			::= { hwHMMEvent 1 }
		hwHMMAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain data of the HMM temperature. (Cleared)"
			::= { hwHMMEvent 2 }
		hwHMMVersionLow NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"An earlier version of HMM is used. (Generated)"
			::= { hwHMMEvent 3 }
		hwHMMVersionLowDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"An earlier version of HMM is used. (Cleared)"
			::= { hwHMMEvent 4 }
	hwBMCEvent OBJECT IDENTIFIER ::= {hwServerTRAPObjectV2 27 }
		hwBMCEEPSelfCheckFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"BMC EEPROM self-test status. (Generated)"
			::= { hwBMCEvent 7 }
		hwBMCEEPSelfCheckFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"BMC EEPROM self-test status. (Cleared)"
			::= { hwBMCEvent 8 }
		hwBMCStatelessCFGFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Stateless computing event in chassis. (Generated)"
			::= { hwBMCEvent 9 }
		hwBMCStatelessCFGFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Stateless computing event in chassis. (Cleared)"
			::= { hwBMCEvent 10 }
		hwBMCVersionChanged NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Version changed."
			::= { hwBMCEvent 11 }
		hwBMCRestartedAfterPowerRestored NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"BMC started after AC power restored."
			::= { hwBMCEvent 13 }
		hwBMCEventCleared NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Event log cleared."
			::= { hwBMCEvent 15 }
		hwBMCEventSpaceExceedThreshold NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Event log is about to full. (Generated)"
			::= { hwBMCEvent 17 }
		hwBMCEventSpaceExceedThresholdDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Event log is about to full. (Cleared)"
			::= { hwBMCEvent 18 }
		hwBMCMMHeartBeatFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"iBMC-MM heartbeat abnormal. (Generated)"
			::= { hwBMCEvent 19 }
		hwBMCMMHeartBeatFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"iBMC-MM heartbeat abnormal. (Cleared)"
			::= { hwBMCEvent 20 }
		hwBMCBaseplaneHeartBeatFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"iBMC-Base heartbeat abnormal. (Generated)"
			::= { hwBMCEvent 21 }
		hwBMCBaseplaneHeartBeatFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"iBMC-Base heartbeat abnormal. (Cleared)"
			::= { hwBMCEvent 22 }
		hwBMCFabricplaneHeartBeatFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"iBMC-Fabric heartbeat abnormal. (Generated)"
			::= { hwBMCEvent 23 }
		hwBMCFabricplaneHeartBeatFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"iBMC-Fabric heartbeat abnormal. (Cleared)"
			::= { hwBMCEvent 24 }
		hwBMCSlaveBMCHeartBeatFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Active-standby iBMC heartbeat abnormal. (Generated)"
			::= { hwBMCEvent 25 }
		hwBMCSlaveBMCHeartBeatFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Active-standby iBMC heartbeat abnormal. (Cleared)"
			::= { hwBMCEvent 26 }
		hwBMCOPLogSpaceExceedThreshold NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Operation log is about to full. (Generated)"
			::= { hwBMCEvent 27 }
		hwBMCOPLogSpaceExceedThresholdDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Operation log is about to full. (Cleared)"
			::= { hwBMCEvent 28 }
		hwBMCSecureLogSpaceExceedThreshold NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Security log is about to full. (Generated)"
			::= { hwBMCEvent 29 }
		hwBMCSecureLogSpaceExceedThresholdDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Security log is about to full. (Cleared)"
			::= { hwBMCEvent 30 }
		hwBMCLSWFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Management LSW chip fault. (Generated)"
			::= { hwBMCEvent 31 }
		hwBMCLSWFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Management LSW chip fault. (Cleared)"
			::= { hwBMCEvent 32 }
		hwBMCResetandStarted NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"iBMC reset and started."
			::= { hwBMCEvent 33 }
		hwBMCCertOverDue NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Certificate expiration check. (Generated)"
			::= { hwBMCEvent 35 }
		hwBMCCertOverDueDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Certificate expiration check. (Cleared)"
			::= { hwBMCEvent 36 }
		hwBMCLostBmaHeartBeat NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"iBMC-BMA heartbeat lost. (Generated)"
			::= { hwBMCEvent 37 }
		hwBMCLostBmaHeartBeatDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"iBMC-BMA heartbeat lost. (Cleared)"
			::= { hwBMCEvent 38 }
		hwBMCNodeBMCHeartBeatFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"iBMC-Node heartbeat abnormal. (Generated)"
			::= { hwBMCEvent 39 }
		hwBMCNodeBMCHeartBeatFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"iBMC-Node heartbeat abnormal. (Cleared)"
			::= { hwBMCEvent 40 }
		hwBMCTimeHopping NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"BMC time hopping."
			::= { hwBMCEvent 41 }
		hwBMCNTPSynchronizeFailed NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to synchronize time with the NTP server. (Generated)"
			::= { hwBMCEvent 43 }
		hwBMCNTPSynchronizeFailedDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to synchronize time with the NTP server. (Cleared)"
			::= { hwBMCEvent 44 }
		hwBMCStandbyMMHeartBeatFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Abnormal heartbeat signal between the iBMC and standby management module. (Generated)"
			::= { hwBMCEvent 45 }
		hwBMCStandbyMMHeartBeatFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Abnormal heartbeat signal between the iBMC and standby management module. (Cleared)"
			::= { hwBMCEvent 46 }
		hwBMCNandFlashRemainingLifeMntr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The service life of the NAND flash is less than threshold. "
			::= { hwBMCEvent 47 }
		hwBMCLicenseOverDue NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The iBMC license enters the grace period and can still be used."
			::= { hwBMCEvent 57 }
		hwBMCLicenseRevoke NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The iBMC license has expired."
			::= { hwBMCEvent 59 }
		hwBMCLicenseFileError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The iBMC license is incorrect. (Generated)"
			::= { hwBMCEvent 61 }
		hwBMCLicenseFileErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The iBMC license is incorrect. (Cleared)"
			::= { hwBMCEvent 62 }
		hwBMCNandFlashOverWrite NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The data written to the NAND flash in last 15 days exceeds threshold. (Generated)"
			::= { hwBMCEvent 67 }
		hwBMCNandFlashOverWriteDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The data written to the NAND flash in last 15 days exceeds threshold. (Cleared)"
			::= { hwBMCEvent 68 }            
	hwBasePlaneEvent OBJECT IDENTIFIER ::= {hwServerTRAPObjectV2 30 }
		hwBasePlaneNotInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base module not installed."
			::= { hwBasePlaneEvent 1 }
		hwBasePlanePowerOff NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base module installed but powered off."
			::= { hwBasePlaneEvent 3 }
		hwBasePlanePowerOnReq NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base module requesting power-on."
			::= { hwBasePlaneEvent 5 }
		hwBasePlaneBeingPowerOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base module in power-on process."
			::= { hwBasePlaneEvent 7 }
		hwBasePlanePoweredOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base module powered on."
			::= { hwBasePlaneEvent 9 }
		hwBasePlanePowerOffReq NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base module requesting power-off."
			::= { hwBasePlaneEvent 11 }
		hwBasePlaneBeingPowerOff NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base module in power-off process."
			::= { hwBasePlaneEvent 13 }
		hwBasePlaneLSWFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base module service LSW fault. (Generated)"
			::= { hwBasePlaneEvent 17 }
		hwBasePlaneLSWFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base module service LSW fault. (Cleared)"
			::= { hwBasePlaneEvent 18 }
		hwBasePlaneLSWOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane LSW overheating minor alarm. (Generated)"
			::= { hwBasePlaneEvent 19 }
		hwBasePlaneLSWOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane LSW overheating minor alarm. (Cleared)"
			::= { hwBasePlaneEvent 20 }
		hwBasePlaneLSWOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane LSW overheating major alarm. (Generated)"
			::= { hwBasePlaneEvent 21 }
		hwBasePlaneLSWOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane LSW overheating major alarm. (Cleared)"
			::= { hwBasePlaneEvent 22 }
		hwBasePlaneLSWAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Base plane LSW temperature. (Generated)"
			::= { hwBasePlaneEvent 23 }
		hwBasePlaneLSWAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Base plane LSW temperature. (Cleared)"
			::= { hwBasePlaneEvent 24 }
		hwBasePlaneLSWLowerVoltMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane switch voltage below lower major threshold. (Generated)"
			::= { hwBasePlaneEvent 25 }
		hwBasePlaneLSWLowerVoltMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane switch voltage below lower major threshold. (Cleared)"
			::= { hwBasePlaneEvent 26 }
		hwBasePlaneLSWOverVoltMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane switch overvoltage major alarm. (Generated)"
			::= { hwBasePlaneEvent 27 }
		hwBasePlaneLSWOverVoltMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane switch overvoltage major alarm. (Cleared)"
			::= { hwBasePlaneEvent 28 }
		hwBasePlaneLSWAccessVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Base plane switch voltage. (Generated)"
			::= { hwBasePlaneEvent 29 }
		hwBasePlaneLSWAccessVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Base plane switch voltage. (Cleared)"
			::= { hwBasePlaneEvent 30 }
		hwBasePlaneCPULowerVoltMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane CPU voltage below lower major threshold. (Generated)"
			::= { hwBasePlaneEvent 31 }
		hwBasePlaneCPULowerVoltMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane CPU voltage below lower major threshold. (Cleared)"
			::= { hwBasePlaneEvent 32 }
		hwBasePlaneCPUOverVoltMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane CPU overvoltage major alarm. (Generated)"
			::= { hwBasePlaneEvent 33 }
		hwBasePlaneCPUOverVoltMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane CPU overvoltage major alarm. (Cleared)"
			::= { hwBasePlaneEvent 34 }
		hwBasePlaneCPUAccessVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Base plane CPU voltage. (Generated)"
			::= { hwBasePlaneEvent 35 }
		hwBasePlaneCPUAccessVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Base plane CPU voltage. (Cleared)"
		    ::= { hwBasePlaneEvent 36 }
		hwBasePlaneCPUOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane CPU overheating minor alarm. (Generated)"
			::= { hwBasePlaneEvent 37 }
		hwBasePlaneCPUOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane CPU overheating minor alarm. (Cleared)"
			::= { hwBasePlaneEvent 38 }
		hwBasePlaneCPUOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane CPU overheating major alarm. (Generated)"
			::= { hwBasePlaneEvent 39 }
		hwBasePlaneCPUOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane CPU overheating major alarm. (Cleared)"
			::= { hwBasePlaneEvent 40 }
		hwBasePlaneCPUAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Base plane CPU temperature. (Generated)"
			::= { hwBasePlaneEvent 41 }
		hwBasePlaneCPUAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Base plane CPU temperature. (Cleared)"
			::= { hwBasePlaneEvent 42 }
		hwBasePlanePSFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane PS fault. (Generated)"
			::= { hwBasePlaneEvent 43 }
		hwBasePlanePSFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Base plane PS fault. (Cleared)"
			::= { hwBasePlaneEvent 44 }
		hwBasePlaneRestart NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane Restart."
			::= { hwBasePlaneEvent 45 }
	hwFabricPlaneEvent OBJECT IDENTIFIER ::= {hwServerTRAPObjectV2 31 }
		hwFabricPlaneLSWVDDLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip VDD undervoltage major alarm. (Generated)"
			::= { hwFabricPlaneEvent 1 }
		hwFabricPlaneLSWVDDLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip VDD undervoltage major alarm. (Cleared)"
			::= { hwFabricPlaneEvent 2 }
		hwFabricPlaneLSWVDDOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip VDD overvoltage major alarm. (Generated)"
			::= { hwFabricPlaneEvent 3 }
		hwFabricPlaneLSWVDDOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip VDD overvoltage major alarm. (Cleared)"
			::= { hwFabricPlaneEvent 4 }
		hwFabricPlaneLSWVcoreLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip Vcore undervoltage major alarm. (Generated)"
			::= { hwFabricPlaneEvent 5 }
		hwFabricPlaneLSWVcoreLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip Vcore undervoltage major alarm. (Cleared)"
			::= { hwFabricPlaneEvent 6 }
		hwFabricPlaneLSWVcoreOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip Vcore overvoltage major alarm. (Generated)"
			::= { hwFabricPlaneEvent 7 }
		hwFabricPlaneLSWVcoreOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip Vcore overvoltage major alarm. (Cleared)"
			::= { hwFabricPlaneEvent 8 }
		hwFabricPlaneLSWOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip overheating minor alarm. (Generated)"
			::= { hwFabricPlaneEvent 9 }
		hwFabricPlaneLSWOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip overheating minor alarm. (Cleared)"
			::= { hwFabricPlaneEvent 10 }
		hwFabricPlaneLSWOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip overheating major alarm. (Generated)"
			::= { hwFabricPlaneEvent 11 }
		hwFabricPlaneLSWOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip overheating major alarm. (Cleared)"
			::= { hwFabricPlaneEvent 12 }
		hwFabricPlaneCPUOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane CPU overheating minor alarm. (Generated)"
			::= { hwFabricPlaneEvent 15 }
		hwFabricPlaneCPUOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane CPU overheating minor alarm. (Cleared)"
			::= { hwFabricPlaneEvent 16 }
		hwFabricPlaneCPUOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane CPU overheating major alarm. (Generated)"
			::= { hwFabricPlaneEvent 17 }
		hwFabricPlaneCPUOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane CPU overheating major alarm. (Cleared)"
			::= { hwFabricPlaneEvent 18 }
		hwFabricPlaneLSWFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip fault. (Generated)"
			::= { hwFabricPlaneEvent 21 }
		hwFabricPlaneLSWFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane LSW chip fault. (Cleared)"
			::= { hwFabricPlaneEvent 22 }
		hwFabricPlaneNotInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric module not installed."
			::= { hwFabricPlaneEvent 23 }
		hwFabricPlanePowerOff NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric module installed but powered off."
			::= { hwFabricPlaneEvent 25 }
		hwFabricPlaneReqPowerOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric module requesting power-on."
			::= { hwFabricPlaneEvent 27 }
		hwFabricPlaneBeingPoweredOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric module in power-on process."
			::= { hwFabricPlaneEvent 29 }
		hwFabricPlanePoweredOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric module powered on."
			::= { hwFabricPlaneEvent 31 }
		hwFabricPlaneReqPoweredOff NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric module requesting power-off."
			::= { hwFabricPlaneEvent 33 }
		hwFabricPlaneInProgressPoweredOff NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric module in power-off process."
			::= { hwFabricPlaneEvent 35 }
		hwFabricPlaneLSWAccessVDDFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Fabric plane LSW chip VDD voltage. (Generated)"
			::= { hwFabricPlaneEvent 39 }
		hwFabricPlaneLSWAccessVDDFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Fabric plane LSW chip VDD voltage. (Cleared)"
			::= { hwFabricPlaneEvent 40 }
		hwFabricPlaneLSWAccessVcoreFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Fabric plane LSW chip Vcore voltage. (Generated)"
			::= { hwFabricPlaneEvent 41 }
		hwFabricPlaneLSWAccessVcoreFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Fabric plane LSW chip Vcore voltage. (Cleared)"
			::= { hwFabricPlaneEvent 42 }
		hwFabricPlaneLSWAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Fabric plane LSW temperature. (Generated)"
			::= { hwFabricPlaneEvent 43 }
		hwFabricPlaneLSWAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Fabric plane LSW temperature. (Cleared)"
			::= { hwFabricPlaneEvent 44 }
		hwFabricPlaneLSWAccessCPUTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Fabric plane CPU temperature. (Generated)"
			::= { hwFabricPlaneEvent 45 }
		hwFabricPlaneLSWAccessCPUTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Fabric plane CPU temperature. (Cleared)"
			::= { hwFabricPlaneEvent 46 }
		hwFabricPlaneSWLowerVoltMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch voltage below lower major threshold. (Generated)"
			::= { hwFabricPlaneEvent 47 }
		hwFabricPlaneSWLowerVoltMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch voltage below lower major threshold. (Cleared)"
			::= { hwFabricPlaneEvent 48 }
		hwFabricPlaneSWOverVoltMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch overvoltage major alarm. (Generated)"
			::= { hwFabricPlaneEvent 49 }
		hwFabricPlaneSWOverVoltMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch overvoltage major alarm. (Cleared)"
			::= { hwFabricPlaneEvent 50 }	
		hwFabricPlaneSWAccessVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Fabric plane switch voltage. (Generated)"
			::= { hwFabricPlaneEvent 51 }
		hwFabricPlaneSWAccessVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read Fabric plane switch voltage. (Cleared)"
			::= { hwFabricPlaneEvent 52 }
		hwFabricPlaneSWOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch overheating minor alarm. (Generated)"
			::= { hwFabricPlaneEvent 53 }
		hwFabricPlaneSWOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch overheating minor alarm. (Cleared)"
			::= { hwFabricPlaneEvent 54 }
		hwFabricPlaneSWOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch overheating major alarm. (Generated)"
			::= { hwFabricPlaneEvent 55 }
		hwFabricPlaneSWOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch overheating major alarm. (Cleared)"
			::= { hwFabricPlaneEvent 56 }
		hwFabricPlaneSWFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch fault. (Generated)"
			::= { hwFabricPlaneEvent 57 }
		hwFabricPlaneSWFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch fault. (Cleared)"
			::= { hwFabricPlaneEvent 58 }
		hwFabricPlaneSWEEPROMFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch EEPROM fault. (Generated)"
			::= { hwFabricPlaneEvent 59 }
		hwFabricPlaneSWEEPROMFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch EEPROM fault. (Cleared)"
			::= { hwFabricPlaneEvent 60 }
		hwFabricPlaneSWClock NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch clock abnormal. (Generated)"
			::= { hwFabricPlaneEvent 61 }
		hwFabricPlaneSWClockDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane switch clock abnormal. (Cleared)"
			::= { hwFabricPlaneEvent 62 }
		hwFabricPlaneRestart NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fabric plane Restart."
			::= { hwFabricPlaneEvent 63 }
		hwFabricPlaneSWAccessSVIDFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the switch chip SVID value for the Fabric plane. (Generated)"
			::= { hwFabricPlaneEvent 65 }
		hwFabricPlaneSWAccessSVIDFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the switch chip SVID value for the Fabric plane. (Cleared)"
			::= { hwFabricPlaneEvent 66 }		
	hwSwitchMezzEvent OBJECT IDENTIFIER ::= {hwServerTRAPObjectV2 32 }
		hwSwitchMezzFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card fault. (Generated)"
			::= { hwSwitchMezzEvent 5 }
		hwSwitchMezzFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card fault. (Cleared)"
			::= { hwSwitchMezzEvent 6 }
		hwSwitchMezz2V5LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 2.5V undervoltage major alarm. (Generated)"
			::= { hwSwitchMezzEvent 7 }
		hwSwitchMezz2V5LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 2.5V undervoltage major alarm. (Cleared)"
			::= { hwSwitchMezzEvent 8 }
		hwSwitchMezz2V5OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 2.5V overvoltage major alarm. (Generated)"
			::= { hwSwitchMezzEvent 9 }
		hwSwitchMezz2V5OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 2.5V overvoltage major alarm. (Cleared)"
			::= { hwSwitchMezzEvent 10 }
		hwSwitchMezz3V3LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 3.3V undervoltage major alarm. (Generated)"
			::= { hwSwitchMezzEvent 11 }
		hwSwitchMezz3V3LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 3.3V undervoltage major alarm. (Cleared)"
			::= { hwSwitchMezzEvent 12 }
		hwSwitchMezz3V3OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 3.3V overvoltage major alarm. (Generated)"
			::= { hwSwitchMezzEvent 13 }
		hwSwitchMezz3V3OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 3.3V overvoltage major alarm. (Cleared)"
			::= { hwSwitchMezzEvent 14 }
		hwSwitchMezz12VLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 12V undervoltage major alarm. (Generated)"
			::= { hwSwitchMezzEvent 15 }
		hwSwitchMezz12VLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 12V undervoltage major alarm. (Cleared)"
			::= { hwSwitchMezzEvent 16 }
		hwSwitchMezz12VOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 12V overvoltage major alarm. (Generated)"
			::= { hwSwitchMezzEvent 17 }
		hwSwitchMezz12VOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 12V overvoltage major alarm. (Cleared)"
			::= { hwSwitchMezzEvent 18 }
		hwSwitchMezz1VLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 1V undervoltage major alarm. (Generated)"
			::= { hwSwitchMezzEvent 19 }
		hwSwitchMezz1VLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 1V undervoltage major alarm. (Cleared)"
			::= { hwSwitchMezzEvent 20 }
		hwSwitchMezz1VOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 1V overvoltage major alarm. (Generated)"
			::= { hwSwitchMezzEvent 21 }
		hwSwitchMezz1VOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 1V overvoltage major alarm. (Cleared)"
			::= { hwSwitchMezzEvent 22 }
		hwSwitchMezz1V8LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 1.8V undervoltage major alarm. (Generated)"
			::= { hwSwitchMezzEvent 23 }
		hwSwitchMezz1V8LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 1.8V undervoltage major alarm. (Cleared)"
			::= { hwSwitchMezzEvent 24 }
		hwSwitchMezz1V8OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 1.8V overvoltage major alarm. (Generated)"
			::= { hwSwitchMezzEvent 25 }
		hwSwitchMezz1V8OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 1.8V overvoltage major alarm. (Cleared)"
			::= { hwSwitchMezzEvent 26 }
		hwSwitchMezz1V5LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 1.5V undervoltage major alarm. (Generated)"
			::= { hwSwitchMezzEvent 27 }
		hwSwitchMezz1V5LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 1.5V undervoltage major alarm. (Cleared)"
			::= { hwSwitchMezzEvent 28 }
		hwSwitchMezz1V5OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 1.5V overvoltage major alarm. (Generated)"
			::= { hwSwitchMezzEvent 29 }
		hwSwitchMezz1V5OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card 1.5V overvoltage major alarm. (Cleared)"
			::= { hwSwitchMezzEvent 30 }
		hwSwitchMezzStdby3V3LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card standby 3.3V undervoltage major alarm. (Generated)"
			::= { hwSwitchMezzEvent 31 }
		hwSwitchMezzStdby3V3LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card standby 3.3V undervoltage major alarm. (Cleared)"
			::= { hwSwitchMezzEvent 32 }
		hwSwitchMezzStdby3V3OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card standby 3.3V overvoltage major alarm. (Generated)"
			::= { hwSwitchMezzEvent 33 }
		hwSwitchMezzStdby3V3OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card standby 3.3V overvoltage major alarm. (Cleared)"
			::= { hwSwitchMezzEvent 34 }
		hwSwitchMezzNotInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card not installed."
			::= { hwSwitchMezzEvent 35 }
		hwSwitchMezzPowerOff NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card installed but powered off."
			::= { hwSwitchMezzEvent 37 }
		hwSwitchMezzReqPowerOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card requesting power-on."
			::= { hwSwitchMezzEvent 39 }
		hwSwitchMezzBeingPoweredOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card in power-on process."
			::= { hwSwitchMezzEvent 41 }
		hwSwitchMezzPoweredOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card powered on."
			::= { hwSwitchMezzEvent 43 }
		hwSwitchMezzReqPowerOff NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card requesting power-off."
			::= { hwSwitchMezzEvent 45 }
		hwSwitchMezzBeingPoweredOff NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card in power-off process."
			::= { hwSwitchMezzEvent 47 }
		hwSwitchMezzAccess2V5Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card 2.5V voltage. (Generated)"
			::= { hwSwitchMezzEvent 51 }
		hwSwitchMezzAccess2V5FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card 2.5V voltage. (Cleared)"
			::= { hwSwitchMezzEvent 52 }
		hwSwitchMezzAccess3V3Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card 3.3V voltage. (Generated)"
			::= { hwSwitchMezzEvent 53 }
		hwSwitchMezzAccess3V3FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card 3.3V voltage. (Cleared)"
			::= { hwSwitchMezzEvent 54 }
		hwSwitchMezzAccess12VFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card 12V voltage. (Generated)"
			::= { hwSwitchMezzEvent 55 }
		hwSwitchMezzAccess12VFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card 12V voltage. (Cleared)"
			::= { hwSwitchMezzEvent 56 }
		hwSwitchMezzAccess1V5Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card 1.5V voltage. (Generated)"
			::= { hwSwitchMezzEvent 57 }
		hwSwitchMezzAccess1V5FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card 1.5V voltage. (Cleared)"
			::= { hwSwitchMezzEvent 58 }
		hwSwitchMezzAccess1VFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card 1V voltage. (Generated)"
			::= { hwSwitchMezzEvent 59 }
		hwSwitchMezzAccess1VFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card 1V voltage. (Cleared)"
			::= { hwSwitchMezzEvent 60 }
		hwSwitchMezzAccessStdby3V3Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card standby 3.3V voltage. (Generated)"
			::= { hwSwitchMezzEvent 61 }
		hwSwitchMezzAccessStdby3V3FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card standby 3.3V voltage. (Cleared)"
			::= { hwSwitchMezzEvent 62 }
		hwSwitchMezzAccessStdby1V8Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card 1.8V voltage. (Generated)"
			::= { hwSwitchMezzEvent 63 }
		hwSwitchMezzAccessStdby1V8FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read mezzanine card 1.8V voltage. (Cleared)"
			::= { hwSwitchMezzEvent 64 }
        hwSwitchMezzPSFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card ps fault. (Generated)"
			::= { hwSwitchMezzEvent 65 }
		hwSwitchMezzPSFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mezzanine card ps fault. (Cleared)"
			::= { hwSwitchMezzEvent 66 }
	hwSDEvent OBJECT IDENTIFIER ::= {hwServerTRAPObjectV2 34 }
		hwSDInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card installed."
			::= { hwSDEvent 1 }
		hwSDRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card removed."
			::= { hwSDEvent 3 }
		hwSDSRAIDArrayInvalid NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card RAID lost. (Generated)"
			::= { hwSDEvent 5 }
		hwSDSRAIDArrayInvalidDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card RAID lost. (Cleared)"
			::= { hwSDEvent 6 }
		hwSDRAIDRebuildStart NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card starting to rebuild RAID."
			::= { hwSDEvent 7 }
		hwSDRAIDRebuildFinish NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card RAID rebuild completed."
			::= { hwSDEvent 9 }
		hwSDRAIDRebuildFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card RAID rebuild failed. (Generated)"
			::= { hwSDEvent 11 }
		hwSDRAIDRebuildFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card RAID rebuild failed. (Cleared)"
			::= { hwSDEvent 12 }
		hwSDFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card fault. (Generated)"
			::= { hwSDEvent 13 }
		hwSDFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card fault. (Cleared)"
			::= { hwSDEvent 14 }
		hwSDDetectCardFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card not detected. (Generated)"
			::= { hwSDEvent 15 }
		hwSDDetectCardFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card not detected. (Cleared)"
			::= { hwSDEvent 16 }
	hwTPMEvent OBJECT IDENTIFIER ::= {hwServerTRAPObjectV2 35 }
		hwTPMSelfTestFailed NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"TPM self-test failed. (Generated)"
			::= { hwTPMEvent 1 }
		hwTPMSelfTestFailedDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"TPM self-test failed. (Cleared)"
			::= { hwTPMEvent 2 }
	hwIOBoardEvent OBJECT IDENTIFIER ::= {hwServerTRAPObjectV2 36 }
		hwIOBoardInletMOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Middle of I/O board air inlet overheating minor alarm. (Generated)"
			::= { hwIOBoardEvent 1 }
		hwIOBoardInletMOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Middle of I/O board air inlet overheating minor alarm. (Cleared)"
			::= { hwIOBoardEvent 2 }
		hwIOBoardInletROverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Right of I/O board air inlet overheating minor alarm. (Generated)"
			::= { hwIOBoardEvent 3 }
		hwIOBoardInletROverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Right of I/O board air inlet overheating minor alarm. (Cleared)"
			::= { hwIOBoardEvent 4 }
		hwIOBoardInletLOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Left of I/O board air inlet overheating minor alarm. (Generated)"
			::= { hwIOBoardEvent 5 }
		hwIOBoardInletLOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Left of I/O board air inlet overheating minor alarm. (Cleared)"
			::= { hwIOBoardEvent 6 }
		hwIOBoardInletMAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read temperature of the middle of I/O board air inlet. (Generated)"
			::= { hwIOBoardEvent 7 }
		hwIOBoardInletMAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read temperature of the middle of I/O board air inlet. (Cleared)"
			::= { hwIOBoardEvent 8 }
		hwIOBoardInletRAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read temperature of the right of I/O board air inlet. (Generated)"
			::= { hwIOBoardEvent 9 }
		hwIOBoardInletRAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read temperature of the right of I/O board air inlet. (Cleared)"
			::= { hwIOBoardEvent 10 }
		hwIOBoardInletLAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read temperature of the left of I/O board air inlet. (Generated)"
			::= { hwIOBoardEvent 11 }
		hwIOBoardInletLAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read temperature of the left of I/O board air inlet. (Cleared)"
			::= { hwIOBoardEvent 12 }
		hwIOBoardCPLDSelfTestFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board CPLD self-test failed. (Generated)"
			::= { hwIOBoardEvent 13 }
		hwIOBoardCPLDSelfTestFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board CPLD self-test failed. (Cleared)"
			::= { hwIOBoardEvent 14 }
		hwIOBoard12VOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board 12V overvoltage major alarm. (Generated)"
			::= { hwIOBoardEvent 15 }
		hwIOBoard12VOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board 12V overvoltage major alarm. (Cleared)"
			::= { hwIOBoardEvent 16 }
		hwIOBoard12VLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board 12V undervoltage major alarm. (Generated)"
			::= { hwIOBoardEvent 17 }
		hwIOBoard12VLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board 12V undervoltage major alarm. (Cleared)"
			::= { hwIOBoardEvent 18 }
		hwIOBoardAccess12VFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read I/O board 12V voltage. (Generated)"
			::= { hwIOBoardEvent 19 }
		hwIOBoardAccess12VFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read I/O board 12V voltage. (Cleared)"
			::= { hwIOBoardEvent 20 }
		hwIOBoardClockSignalLost NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board clock signals lost. (Generated)"
			::= { hwIOBoardEvent 21 }
		hwIOBoardClockSignalLostDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board clock signals lost. (Cleared)"
			::= { hwIOBoardEvent 22 }
		hwIOBoardStdby3V3OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board standby 3.3V overvoltage major alarm. (Generated)"
			::= { hwIOBoardEvent 23 }
		hwIOBoardStdby3V3OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board standby 3.3V overvoltage major alarm. (Cleared)"
			::= { hwIOBoardEvent 24 }
		hwIOBoardStdby3V3LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board standby 3.3V undervoltage major alarm. (Generated)"
			::= { hwIOBoardEvent 25 }
		hwIOBoardStdby3V3LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board standby 3.3V undervoltage major alarm. (Cleared)"
			::= { hwIOBoardEvent 26 }
		hwIOBoardAccessStdby3V3Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read I/O board standby 3.3V voltage. (Generated)"
			::= { hwIOBoardEvent 27 }
		hwIOBoardAccessStdby3V3FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read I/O board standby 3.3V voltage. (Cleared)"
			::= { hwIOBoardEvent 28 }
		hwIOBoardClockPower NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power supplies to clock chips on the IO board abnormal. (Generated)"
			::= { hwIOBoardEvent 29 }
		hwIOBoardClockPowerDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power supplies to clock chips on the IO board abnormal. (Cleared)"
			::= { hwIOBoardEvent 30 }
		hwIOBoardClock NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"IO board clock chips abnormal. (Generated)"
			::= { hwIOBoardEvent 31 }
		hwIOBoardClockDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"IO board clock chips abnormal. (Cleared)"
			::= { hwIOBoardEvent 32 }
		hwIOBoardPower NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"IO board power signal abnormal. (Generated)"
			::= { hwIOBoardEvent 33 }
		hwIOBoardPowerDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"IO board power signal abnormal. (Cleared)"
			::= { hwIOBoardEvent 34 }
	    hwIOBoardVCC3V3OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board VCC 3.3V overvoltage major alarm. (Generated)"
			::= { hwIOBoardEvent 35 }
		hwIOBoardVCC3V3OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board VCC 3.3V overvoltage major alarm. (Cleared)"
			::= { hwIOBoardEvent 36 }
		hwIOBoardVCC3V3LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board VCC 3.3V undervoltage major alarm. (Generated)"
			::= { hwIOBoardEvent 37 }
		hwIOBoardVCC3V3LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"I/O board VCC 3.3V undervoltage major alarm. (Cleared)"
			::= { hwIOBoardEvent 38 }
		hwIOBoardAccessVCC3V3Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read I/O board VCC 3.3V voltage. (Generated)"
			::= { hwIOBoardEvent 39 }
		hwIOBoardAccessVCC3V3FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read I/O board VCC 3.3V voltage. (Cleared)"
			::= { hwIOBoardEvent 40 }
		hwIOBoardAccessBoardIDFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain data of the board id. (Generated)"
			::= { hwIOBoardEvent 41 }
		hwIOBoardAccessBoardIDFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain data of the board id .(Cleared)"
			::= { hwIOBoardEvent 42 }
		hwIOBoardInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"IO board  installed."
			::= { hwIOBoardEvent 43 }
		hwIOBoardRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"IO board  removed."
			::= { hwIOBoardEvent 45 }
		hwREEACLostMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The entire REE enclosure is powered off. (Generated)"
			::= { hwIOBoardEvent 47 }
		hwREEACLostMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The entire REE enclosure is powered off. (Cleared)"
			::= { hwIOBoardEvent 48 }
		hwIOBoardStartUpOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System is forcibly shut down due to high temperature of the soft-start circuit I/O board. (Generated)"
			::= { hwIOBoardEvent 49 }
		hwIOBoardStartUpOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System is forcibly shut down due to high temperature of the soft-start circuit I/O board. (Cleared)"
			::= { hwIOBoardEvent 50 }
		hwIOBoardInletLOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Left of the I/O board air inlet overtemperature. (Generated)"
			::= { hwIOBoardEvent 51 }
		hwIOBoardInletLOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Left of the I/O board air inlet overtemperature. (Cleared)"
			::= { hwIOBoardEvent 52 }
		hwIOBoardSlotUnavailable NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"For the model, slot of the I/O board is unavailable. (Generated)"
			::= { hwIOBoardEvent 53 }
		hwIOBoardSlotUnavailableDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"For the model, slot of the I/O board is unavailable. (Cleared)"
			::= { hwIOBoardEvent 54 }
	hwCPUBoardEvent OBJECT IDENTIFIER ::= {hwServerTRAPObjectV2 37 }
		hwCPUBoardOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU board overheating minor alarm. (Generated)"
			::= { hwCPUBoardEvent 1 }
		hwCPUBoardOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU board overheating minor alarm. (Cleared)"
			::= { hwCPUBoardEvent 2 }
		hwCPUBoardAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU board temperature. (Generated)"
			::= { hwCPUBoardEvent 3 }
		hwCPUBoardAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU board temperature. (Cleared)"
			::= { hwCPUBoardEvent 4 }
		hwCPUBoardCPLDSelfTestFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU board CPLD self-test failed. (Generated)"
			::= { hwCPUBoardEvent 5 }
		hwCPUBoardCPLDSelfTestFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU board CPLD self-test failed. (Cleared)"
			::= { hwCPUBoardEvent 6 }
		hwCPUBoardClockSignalLost NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU Board clock signals lost. (Generated)"
			::= { hwCPUBoardEvent 7 }
		hwCPUBoardClockSignalLostDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU Board clock signals lost. (Cleared)"
			::= { hwCPUBoardEvent 8 }
		hwCPUBoardStartUpOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System is forcibly shut down due to high temperature of the soft-start circuit. (Generated)"
			::= { hwCPUBoardEvent 9 }
		hwCPUBoardStartUpOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System is forcibly shut down due to high temperature of the soft-start circuit. (Cleared)"
			::= { hwCPUBoardEvent 10 }
	hwPCHEvent OBJECT IDENTIFIER ::= {hwServerTRAPObjectV2 40 }
		hwPCHOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH overheating minor alarm. (Generated)"
			::= { hwPCHEvent 1 }
		hwPCHOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH overheating minor alarm. (Cleared)"
			::= { hwPCHEvent 2 }
		hwPCHUncorrectableErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH MCE/AER error. (Generated)"
			::= { hwPCHEvent 3 }
		hwPCHUncorrectableErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH MCE/AER error. (Cleared)"
			::= { hwPCHEvent 4 }
		hwPCHLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Southbridge undervoltage major alarm. (Generated)"
			::= { hwPCHEvent 5 }
		hwPCHLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Southbridge undervoltage major alarm. (Cleared)"
			::= { hwPCHEvent 6 }
		hwPCHOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Southbridge overvoltage major alarm. (Generated)"
			::= { hwPCHEvent 7 }
		hwPCHOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Southbridge overvoltage major alarm. (Cleared)"
			::= { hwPCHEvent 8 }
		hwPCHClockSignalLost NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Southbridge clock lost. (Generated)"
			::= { hwPCHEvent 9 }
		hwPCHClockSignalLostDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Southbridge clock lost. (Cleared)"
			::= { hwPCHEvent 10 }
		hwPCHAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCH temperature. (Generated)"
			::= { hwPCHEvent 11 }
		hwPCHAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCH temperature. (Cleared)"
			::= { hwPCHEvent 12 }
		hwPCHAccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCH voltage. (Generated)"
			::= { hwPCHEvent 13 }
		hwPCHAccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCH voltage. (Cleared)"
			::= { hwPCHEvent 14 }
		hwPCHVpvnnOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH VPVNN overvoltage. (Generated)"
			::= { hwPCHEvent 15 }
		hwPCHVpvnnOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH VPVNN overvoltage. (Cleared)"
			::= { hwPCHEvent 16 }
		hwPCHVpvnnLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH VPVNN undervoltage. (Generated)"
			::= { hwPCHEvent 17 }
		hwPCHVpvnnLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH VPVNN undervoltage. (Cleared)"
			::= { hwPCHEvent 18 }
		hwPCHAccessVpvnnVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCH VPVNN voltage. (Generated)"
			::= { hwPCHEvent 19 }
		hwPCHAccessVpvnnVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCH VPVNN voltage. (Cleared)"
			::= { hwPCHEvent 20 }
		hwPCHPRIMVoltOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH PRIM 1.05V overvoltage. (Generated)"
			::= { hwPCHEvent 21 }
		hwPCHPRIMVoltOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH PRIM 1.05V overvoltage. (Cleared)"
			::= { hwPCHEvent 22 }
		hwPCHPRIMVoltLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH PRIM 1.05V undervoltage. (Generated)"
			::= { hwPCHEvent 23 }
		hwPCHPRIMVoltLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH PRIM 1.05V undervoltage. (Cleared)"
			::= { hwPCHEvent 24 }
		hwPCHPRIMAccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCH PRIM 1.05V voltage. (Generated)"
			::= { hwPCHEvent 25 }
		hwPCHPRIMAccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCH PRIM 1.05V voltage. (Cleared)"
			::= { hwPCHEvent 26 }
		hwPCHIOVoltLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH IO undervoltage. (Generated)"
			::= { hwPCHEvent 27 }
		hwPCHIOVoltLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH IO undervoltage. (Cleared)"
			::= { hwPCHEvent 28 }
		hwPCHIOVoltOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH IO overvoltage. (Generated)"
			::= { hwPCHEvent 29 }
		hwPCHIOVoltOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH IO overvoltage. (Cleared)"
			::= { hwPCHEvent 30 }
		hwPCHIOAccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCH IO voltage. (Generated)"
			::= { hwPCHEvent 31 }
		hwPCHIOAccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCH IO voltage. (Cleared)"
			::= { hwPCHEvent 32 }
		hwPCHPvnnLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH pvnn undervoltage. (Generated)"
			::= { hwPCHEvent 33 }
		hwPCHPvnnLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH pvnn undervoltage. (Cleared)"
			::= { hwPCHEvent 34 }
		hwPCHPvnnOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH pvnn overvoltage. (Generated)"
			::= { hwPCHEvent 35 }
		hwPCHPvnnOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH pvnn overvoltage. (Cleared)"
			::= { hwPCHEvent 36 }
		hwPCHOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH overtemperature major alarm. (Generated)"
			::= { hwPCHEvent 37 }
		hwPCHOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH overtemperature major alarm. (Cleared)"
			::= { hwPCHEvent 38 }
        hwPCHStdbyLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH standby undervoltage. (Generated)"
			::= { hwPCHEvent 45 }
		hwPCHStdbyLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH standby undervoltage. (Cleared)"
			::= { hwPCHEvent 46 }
		hwPCHStdbyOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH standby overvoltage. (Generated)"
			::= { hwPCHEvent 47 }
		hwPCHStdbyOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH standby overvoltage. (Cleared)"
			::= { hwPCHEvent 48 }
        hwPCHAccessStdbyFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCH standby voltage. (Generated)"
			::= { hwPCHEvent 49 }
		hwPCHAccessStdbyFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCH standby voltage. (Cleared)"
			::= { hwPCHEvent 50 }
		hwPCHCEHardFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH health status degradation detected by PFAE. (Generated)"
			::= { hwPCHEvent 51 }
		hwPCHCEHardFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCH health status degradation detected by PFAE. (Cleared)"
			::= { hwPCHEvent 52 }
	hwCableEvent OBJECT IDENTIFIER ::= {hwServerTRAPObjectV2 41 }
		hwCableSASIncorrectConnection NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect SAS cable connection. (Generated)"
			::= { hwCableEvent 1 }
		hwCableSASIncorrectConnectionDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect SAS cable connection. (Cleared)"
			::= { hwCableEvent 2 }
		hwCableCPLDIncorrectConnection NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Improper CPLD signal cable connection. (Generated)"
			::= { hwCableEvent 3 }
		hwCableCPLDIncorrectConnectionDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Improper CPLD signal cable connection. (Cleared)"
			::= { hwCableEvent 4 }
		hwCableQPILinkFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Abnormal QPI link between CPUs. (Generated)"
			::= { hwCableEvent 5 }
		hwCableQPILinkFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Abnormal QPI link between CPUs. (Cleared)"
			::= { hwCableEvent 6 }
		hwCableCXPLinkFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CXP cable lane drop or some logical link down. (Generated)"
			::= { hwCableEvent 7 }
		hwCableCXPLinkFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CXP cable lane drop or some logical link down. (Cleared)"
			::= { hwCableEvent 8 }
		hwCableCXPLinkDown NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CXP cable link down major alarm. (Generated)"
			::= { hwCableEvent 9 }
		hwCableCXPLinkDownDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CXP cable link down major alarm. (Cleared)"
			::= { hwCableEvent 10 }
		hwCableQPILinkDegrade NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU QPI connection degraded. (Generated)"
			::= { hwCableEvent 11 }
		hwCableQPILinkDegradeDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU QPI connection degraded. (Cleared)"
			::= { hwCableEvent 12 }
		hwCablePSBackplaneDisconnection NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Improper PS back plane cable connection. (Generated)"
			::= { hwCableEvent 13 }
		hwCablePSBackplaneDisconnectionDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Improper PS back plane cable connection. (Cleared)"
			::= { hwCableEvent 14 }
		hwCableFanBackplaneDisconnection NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Improper fan back plane cable connection. (Generated)"
			::= { hwCableEvent 15 }
		hwCableFanBackplaneDisconnectionDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Improper fan back plane cable connection. (Cleared)"
			::= { hwCableEvent 16 }
		hwCableAggregationPortDisconnection NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Improper aggregation port cable connection. (Generated)"
			::= { hwCableEvent 17 }
		hwCableAggregationPortDisconnectionDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Improper aggregation port cable connection. (Cleared)"
			::= { hwCableEvent 18 }
		hwCableSLIMIncorrectConnection NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SLIM cable connection is abnormal. (Generated)"
			::= { hwCableEvent 19 }
		hwCableSLIMIncorrectConnectionDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SLIM cable connection is abnormal. (Cleared)"
			::= { hwCableEvent 20 }
		hwCableQPILinkCEHardFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU QPI/UPI link health status degradation detected by PFAE. (Generated)"
			::= { hwCableEvent 21 }
		hwCableQPILinkCEHardFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU QPI/UPI link health status degradation detected by PFAE. (Cleared)"
			::= { hwCableEvent 22 }
		hwCablePowerIncorrectConnection NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power cable is connected incorrectly. (Generated)"
			::= { hwCableEvent 23 }
		hwCablePowerIncorrectConnectionDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power cable is connected incorrectly. (Cleared)"
			::= { hwCableEvent 24 }
		hwCableSASRedriverConfigureFail NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to configure the SAS. (Generated)"
			::= { hwCableEvent 25 }
		hwCableSASRedriverConfigureFailDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to configure the SAS. (Cleared)"
			::= { hwCableEvent 26 }
		hwCableSLIMNotPresent NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SLIM cable is not connected. (Generated)"
			::= { hwCableEvent 27 }
		hwCableSLIMNotPresentDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SLIM cable is not connected. (Cleared)"
			::= { hwCableEvent 28 }
		hwCableSASPCIeIncorrectConnection NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect SAS/PCIe cable connection. (Generated)"
			::= { hwCableEvent 29 }
		hwCableSASPCIeIncorrectConnectionDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect SAS/PCIe cable connection. (Cleared)"
			::= { hwCableEvent 30 }		
	hwPortEvent OBJECT IDENTIFIER ::= {hwServerTRAPObjectV2 42 }
		hwPortDisconnected NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NIC port link down. (Generated)"
			::= { hwPortEvent 1 }
		hwPortConnected NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NIC port link down. (Cleared)"
			::= { hwPortEvent 2 }
		hwPortInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Port connected."
			::= { hwPortEvent 5 }
		hwPortRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Port removed."
			::= { hwPortEvent 7 }
		hwPortFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Port fault. (Generated)"
			::= { hwPortEvent 9 }
		hwPortFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Port fault. (Cleared)"
			::= { hwPortEvent 10 }
		hwPortNIPortDisconnected NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NCM NI port disconnected. (Generated)"
			::= { hwPortEvent 11 }
		hwPortNIPortDisconnectedDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NCM NI port disconnected. (Cleared)"
			::= { hwPortEvent 12 }
		hwPortOpticalModuleVoltageAlarm NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Optical module voltage major alarm. (Generated)"
			::= { hwPortEvent 15 }
		hwPortOpticalModuleVoltageAlarmDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Optical module voltage major alarm. (Cleared)"
			::= { hwPortEvent 16 }
		hwPortOpticalModulePowerAlarm NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Optical module power major alarm. (Generated)"
			::= { hwPortEvent 23 }
		hwPortOpticalModulePowerAlarmDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Optical module power major alarm. (Cleared)"
			::= { hwPortEvent 24 }
		hwPortOpticalModuleSpeedMismatch NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NIC and optical module speeds mismatch. (Generated)"
			::= { hwPortEvent 39 }
		hwPortOpticalModuleSpeedMismatchDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"NIC and optical module speeds mismatch. (Cleared)"
			::= { hwPortEvent 40 }
		hwPortOAMLostLink NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"OAM Lost Link. (Generated)"
			::= { hwPortEvent 41 }
		hwPortOAMLostLinkDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"OAM Lost Link. (Cleared)"
			::= { hwPortEvent 42 }
		hwPortOAMErrorPackage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"OAM Error Package. (Generated)"
			::= { hwPortEvent 43 }
		hwPortOAMErrorPackageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"OAM Error Package. (Cleared)"
			::= { hwPortEvent 44 }
		hwPortConfigureFail NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to configure the PHY port.(Generated)"
			::= { hwPortEvent 45 }
		hwPortConfigureFailDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to configure the PHY port.(Cleared)"
			::= { hwPortEvent 46 }
	hwPHYEvent OBJECT IDENTIFIER ::= {hwServerTRAPObjectV2 44 }
		hwPHYMDIOErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PHY fault. (Generated)"
			::= { hwPHYEvent 1 }
		hwPHYMDIOErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PHY fault. (Cleared)"
			::= { hwPHYEvent 2 }
		hwSASPHYErrIncreasedTooFast NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SAS PHY bit error increased too fast."
			::= { hwPHYEvent 3 }
	hwSystemEvent OBJECT IDENTIFIER ::= {hwServerTRAPObjectV2 45 }
		hwSystemCPUOverLoad NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"High CPU usage. (Generated)"
			::= { hwSystemEvent 1 }
		hwSystemCPUOverLoadDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"High CPU usage. (Cleared)"
			::= { hwSystemEvent 2 }
		hwSystemMemoryOverLoad NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"High memory usage. (Generated)"
			::= { hwSystemEvent 3 }
		hwSystemMemoryOverLoadDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"High memory usage. (Cleared)"
			::= { hwSystemEvent 4 }
		hwSystemPowerFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System powered off exceptionally. (Generated)"
			::= { hwSystemEvent 7 }
		hwSystemPowerFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System powered off exceptionally. (Cleared)"
			::= { hwSystemEvent 8 }
		hwSystemACPIWorkingState NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"ACPI in operating status."
			::= { hwSystemEvent 9 }
		hwSystemACPISoftOffState NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"ACPI in down status."
			::= { hwSystemEvent 11 }
		hwSystemACPINoMemory NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"No memory detected in system POST. (Generated)"
			::= { hwSystemEvent 13 }
		hwSystemACPINoMemoryDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"No memory detected in system POST. (Cleared)"
			::= { hwSystemEvent 14 }
		hwSystemUnknownReasonRestart NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System restarted due to unknown reason."
			::= { hwSystemEvent 15 }
		hwSystemRestartByCommand NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System restarted by system control command."
			::= { hwSystemEvent 17 }
		hwSystemRestartByPowerButton NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System restarted by power button."
			::= { hwSystemEvent 19 }
		hwSystemRestartByWatchDogTmout NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System restarted by watch dog timed out."
			::= { hwSystemEvent 21 }
		hwSystemRestartByTurnOnStrategy NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System restarted as per power-on strategy Turn On."
			::= { hwSystemEvent 23 }
		hwSystemRestartByRestorePreviousStrategy NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System restarted as per power-on strategy Restore Previous State."
			::= { hwSystemEvent 25 }
		hwSystemOSStartNoBootDevice NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"OS failed to start due to lack of boot media."
			::= { hwSystemEvent 27 }
		hwSystemOSStartNoBootDisk NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"OS failed to start due to lack of boot disk."
			::= { hwSystemEvent 29 }
		hwSystemOSStartNoPXEService NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"OS failed to start due to lack of PXE server."
			::= { hwSystemEvent 31 }
		hwSystemOSStartInvalidBootPartition NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"OS failed to start due to invalid boot partition."
			::= { hwSystemEvent 33 }
		hwSystemWTDTmoutNoAction NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"No action upon watch dog timeout. (Generated)"
			::= { hwSystemEvent 35 }
		hwSystemWTDTmoutNoActionDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"No action upon watch dog timeout. (Cleared)"
			::= { hwSystemEvent 36 }
		hwSystemWTDTmoutForceReset NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Forced restart upon watch dog timeout. (Generated)"
			::= { hwSystemEvent 37 }
		hwSystemWTDTmoutForceResetDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Forced restart upon watch dog timeout. (Cleared)"
			::= { hwSystemEvent 38 }
		hwSystemWTDTmoutForcePowerOff NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System power-off upon watch dog timeout. (Generated)"
			::= { hwSystemEvent 39 }
		hwSystemWTDTmoutForcePowerOffDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System power-off upon watch dog timeout. (Cleared)"
			::= { hwSystemEvent 40 }
		hwSystemWTDTmoutForcedPowerOffThenOn NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Forced power cycle upon watch dog timeout. (Generated)"
			::= { hwSystemEvent 41 }
		hwSystemWTDTmoutForcedPowerOffThenOnDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Forced power cycle upon watch dog timeout. (Cleared)"
			::= { hwSystemEvent 42 }
		hwSystemPowerOnTmout NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power-on timed out. (Generated)"
			::= { hwSystemEvent 43 }
		hwSystemPowerOnTmoutDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power-on timed out. (Cleared)"
			::= { hwSystemEvent 44 }
		hwSystemPowerCapFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power capping failed. (Generated)"
			::= { hwSystemEvent 45 }
		hwSystemPowerCapFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power capping failed. (Cleared)"
			::= { hwSystemEvent 46 }
		hwSystemAbnormallyReset NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System information. (Generated)"
			::= { hwSystemEvent 47 }
		hwSystemAbnormallyResetDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System information. (Cleared)"
			::= { hwSystemEvent 48 }
		hwSystemFaultCritical NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System error. (Generated)"
			::= { hwSystemEvent 49 }
		hwSystemFaultCriticalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System error. (Cleared)"
			::= { hwSystemEvent 50 }
		hwSystemDiffCPUModule NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Inconsistent CPU models. (Generated)"
			::= { hwSystemEvent 55 }
		hwSystemDiffCPUModuleDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Inconsistent CPU models. (Cleared)"
			::= { hwSystemEvent 56 }
		hwSystemSuspended NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System suspended during startup. (Generated)"
			::= { hwSystemEvent 57 }
		hwSystemSuspendedDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System suspended during startup. (Cleared)"
			::= { hwSystemEvent 58 }
		hwSystemInconsistenMemoryBoard NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Inconsistent models of memory boards. (Generated)"
			::= { hwSystemEvent 59 }
		hwSystemInconsistenMemoryBoardDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Inconsistent models of memory boards. (Cleared)"
			::= { hwSystemEvent 60 }
		hwSystemInconsistenCPUBoard NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Inconsistent models of CPU boards. (Generated)"
			::= { hwSystemEvent 61 }
		hwSystemInconsistenCPUBoardDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Inconsistent models of CPU boards. (Cleared)"
			::= { hwSystemEvent 62 }
		hwSystemInsufficientCPU NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Insufficient number of CPUs. (Generated)"
			::= { hwSystemEvent 63 }
		hwSystemInsufficientCPUDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Insufficient number of CPUs. (Cleared)"
			::= { hwSystemEvent 64 }
		hwSystemDiffCPUType NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Inconsistent CPU types. (Generated)"
			::= { hwSystemEvent 65 }
		hwSystemDiffCPUTypeDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Inconsistent CPU types. (Cleared)"
			::= { hwSystemEvent 66 }
		hwSystemDiffHPCBoardType NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Inconsistent HPC models. (Generated)"
			::= { hwSystemEvent 67 }
		hwSystemDiffHPCBoardTypeDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Inconsistent HPC models. (Cleared)"
			::= { hwSystemEvent 68 }
		hwSystemMismatchHPCBoardOrCPU NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"HPC type and CPU do not match. (Generated)"
			::= { hwSystemEvent 69 }
		hwSystemMismatchHPCBoardOrCPUDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"HPC type and CPU do not match. (Cleared)"
			::= { hwSystemEvent 70 }
		hwSystemPSUCFGErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect PSU configuration in SCE. (Generated)"
			::= { hwSystemEvent 73 }
		hwSystemPSUCFGErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Incorrect PSU configuration in SCE. (Cleared)"
			::= { hwSystemEvent 74 }
		hwCPUMemoryConfigError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM configuration error. (Generated)"
			::= { hwSystemEvent 75 }
		hwCPUMemoryConfigErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"DIMM configuration error. (Cleared)"
			::= { hwSystemEvent 76 }
		hwCPUMRCFatalError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System critical error detected in memory initialization check. (Generated)"
			::= { hwSystemEvent 77 }
		hwCPUMRCFatalErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System critical error detected in memory initialization check. (Cleared)"
			::= { hwSystemEvent 78 }
		hwNoAvailableMemoryError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"No available memory. (Generated)"
			::= { hwSystemEvent 79 }
		hwNoAvailableMemoryErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"No available memory. (Cleared)"
			::= { hwSystemEvent 80 }
		hwSystemDiskPartitionOverLoad NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"High disk partition usage. (Generated)"
			::= { hwSystemEvent 83 }
		hwSystemDiskPartitionOverLoadDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"High disk partition usage. (Cleared)"
			::= { hwSystemEvent 84 }
		hwSystemMemoryInitializationError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System error with memory initialization. (Generated)"
			::= { hwSystemEvent 87 }
		hwSystemMemoryInitializationErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System error with memory initialization. (Cleared)"
			::= { hwSystemEvent 88 }
		hwSystemMainboardDiskBPMismatch NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard does not match hard disk backplane. (Generated)"
			::= { hwSystemEvent 91}
		hwSystemMainboardDiskBPMismatchDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Mainboard does not match hard disk backplane. (Cleared)"
			::= { hwSystemEvent 92}
		hwSystemAccessPowerFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read the total system power. (Generated)"
			::= { hwSystemEvent 93 }
		hwSystemAccessPowerFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read the total system power. (Cleared)"
			::= { hwSystemEvent 94 }   
		hwSystemProductIndentityFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to identify the product. (Generated)"
			::= { hwSystemEvent 95 }
		hwSystemProductIndentityFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to identify the product. (Cleared)"
			::= { hwSystemEvent 96 }   		
		hwSystemNetworkBandwidthUsageHigh NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"High bandwidth usage at NIC network port. (Generated)"
			::= { hwSystemEvent 97 }
		hwSystemNetworkBandwidthUsageHighDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"High bandwidth usage at NIC network port. (Cleared)"
			::= { hwSystemEvent 98 }
		hwSystemRestartByBMC NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System restarted by the BMC."
			::= { hwSystemEvent 99 }
		hwSystemCPUMismatchChassis NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The chassis does not support high-power CPUs."
			::= { hwSystemEvent 103 }
		hwSystemAbnormalByHardwareError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System is abnormal due to hardware fault. (Generated)"
			::= { hwSystemEvent 105 }
		hwSystemAbnormalByHardwareErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"System is abnormal due to hardware fault. (Cleared)"
			::= { hwSystemEvent 106 }
		hwSystemMMIOResoureNotEnough NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"MMIO resoure not enough. (Generated)"
			::= { hwSystemEvent 107 }
		hwSystemMMIOResoureNotEnoughDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"MMIO resoure not enough. (Cleared)"
			::= { hwSystemEvent 108 }
		hwSystemLegacyIOResoureNotEnough NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Legacy IO resoure not enough. (Generated)"
			::= { hwSystemEvent 109 }
		hwSystemLegacyIOResoureNotEnoughDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Legacy IO resoure not enough. (Cleared)"
			::= { hwSystemEvent 110 }
		hwSystemLegacyOPROMResoureNotEnough NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Legacy OPROM resoure not enough. (Generated)"
			::= { hwSystemEvent 111 }
		hwSystemLegacyOPROMResoureNotEnoughDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Legacy OPROM resoure not enough. (Cleared)"
			::= { hwSystemEvent 112 }
		hwSystemFSReadonly NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"File system is read only. (Generated)"
			::= { hwSystemEvent 113 }
		hwSystemFSReadonlyDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"File system is read only. (Cleared)"
			::= { hwSystemEvent 114 }
	hwPICCard OBJECT IDENTIFIER ::= {hwServerTRAPObjectV2 49 }
		hwPICCard3V3LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 3.3V undervoltage major alarm. (Generated)"
			::= { hwPICCard 1 }
		hwPICCard3V3LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 3.3V undervoltage major alarm. (Cleared)"
			::= { hwPICCard 2 }
		hwPICCard3V3OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 3.3V overvoltage major alarm. (Generated)"
			::= { hwPICCard 3 }
		hwPICCard3V3OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 3.3V overvoltage major alarm. (Cleared)"
			::= { hwPICCard 4 }
		hwPICCard1V2LowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 1.2V undervoltage major alarm. (Generated)"
			::= { hwPICCard 5 }
		hwPICCard1V2LowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 1.2V undervoltage major alarm. (Cleared)"
			::= { hwPICCard 6 }
		hwPICCard1V2OverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 1.2V overvoltage major alarm. (Generated)"
			::= { hwPICCard 7 }
		hwPICCard1V2OverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 1.2V overvoltage major alarm. (Cleared)"
			::= { hwPICCard 8 }
		hwPICCard1VLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 1V undervoltage major alarm. (Generated)"
			::= { hwPICCard 9 }
		hwPICCard1VLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 1V undervoltage major alarm. (Cleared)"
			::= { hwPICCard 10 }
		hwPICCard1VOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 1V overvoltage major alarm. (Generated)"
			::= { hwPICCard 11 }
		hwPICCard1VOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 1V overvoltage major alarm. (Cleared)"
			::= { hwPICCard 12 }
		hwPICCard12VLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 12V undervoltage major alarm. (Generated)"
			::= { hwPICCard 13 }
		hwPICCard12VLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 12V undervoltage major alarm. (Cleared)"
			::= { hwPICCard 14 }
		hwPICCard12VOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 12V overvoltage major alarm. (Generated)"
			::= { hwPICCard 15 }
		hwPICCard12VOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card 12V overvoltage major alarm. (Cleared)"
			::= { hwPICCard 16 }
		hwPICCardOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card overheating minor alarm. (Generated)"
			::= { hwPICCard 17 }
		hwPICCardOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card overheating minor alarm. (Cleared)"
			::= { hwPICCard 18 }
		hwPICCardOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card overheating major alarm. (Generated)"
			::= { hwPICCard 19 }
		hwPICCardOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card overheating major alarm. (Cleared)"
			::= { hwPICCard 20 }
		hwPICCardInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card installed."
			::= { hwPICCard 21 }
		hwPICCardRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card removed."
			::= { hwPICCard 23 }
		hwPICCardPSFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card power failure. (Generated)"
			::= { hwPICCard 25 }
		hwPICCardPSFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card power failure. (Cleared)"
			::= { hwPICCard 26 }
		hwPICCardFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card fault. (Generated)"
			::= { hwPICCard 27 }
		hwPICCardFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card fault. (Cleared)"
			::= { hwPICCard 28 }
		hwPICCardAccess3V3Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PIC card 3.3V voltage. (Generated)"
			::= { hwPICCard 29 }
		hwPICCardAccess3V3FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PIC card 3.3V voltage. (Cleared)"
			::= { hwPICCard 30 }
		hwPICCardAccess1V2Failure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PIC card 1.2V voltage. (Generated)"
			::= { hwPICCard 31 }
		hwPICCardAccess1V2FailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PIC card 1.2V voltage. (Cleared)"
			::= { hwPICCard 32 }
		hwPICCardAccess1VFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PIC card 1V voltage. (Generated)"
			::= { hwPICCard 33 }
		hwPICCardAccess1VFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PIC card 1V voltage. (Cleared)"
			::= { hwPICCard 34 }
		hwPICCardAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PIC card temperature. (Generated)"
			::= { hwPICCard 35 }
		hwPICCardAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PIC card temperature. (Cleared)"
			::= { hwPICCard 36 }
		hwPICCardAccess12VFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PIC card 12V voltage. (Generated)"
			::= { hwPICCard 37 }
		hwPICCardAccess12VFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PIC card 12V voltage. (Cleared)"
			::= { hwPICCard 38 }
        hwPICCardLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card voltage below lower major threshold. (Generated)"
			::= { hwPICCard 39 }
		hwPICCardLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card voltage below lower major threshold. (Cleared)"
			::= { hwPICCard 40 }
        hwPICCardOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card overvoltage major alarm. (Generated)"
			::= { hwPICCard 41 }
		hwPICCardOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card overvoltage major alarm. (Cleared)"
			::= { hwPICCard 42 }
        hwPICCardAccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PIC card voltage. (Generated)"
			::= { hwPICCard 43 }
		hwPICCardAccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PIC card voltage. (Cleared)"
			::= { hwPICCard 44 }
        hwPICCardClockSignalLost NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card clock signals lost. (Generated)"
			::= { hwPICCard 45 }
		hwPICCardClockSignalLostDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PIC card clock signals lost. (Cleared)"
			::= { hwPICCard 46 }
	hwButtonEvent OBJECT IDENTIFIER ::= {hwServerTRAPObjectV2 50 }
		hwButtonPowerButtonPressed NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Power button pressed."
			::= { hwButtonEvent 1 }
		hwButtonUIDButtonpressed NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"UID button pressed."
			::= { hwButtonEvent 3 }
		hwButtonPCIeHotSwapButtonPressed NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe card hot-swap button pressed."
			::= { hwButtonEvent 5 }
	hwExpanderEvent OBJECT IDENTIFIER ::= {hwServerTRAPObjectV2 51 }
		hwExpanderFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk backplane expander fault. (Generated)"
			::= { hwExpanderEvent 1 }
		hwExpanderFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk backplane expander fault. (Cleared)"
			::= { hwExpanderEvent 2 }
		hwExpanderCommFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Communication between expander and RAID card failed. (Generated)"
			::= { hwExpanderEvent 3 }
		hwExpanderCommFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Communication between expander and RAID card failed. (Cleared)"
			::= { hwExpanderEvent 4 }
		hwExpanderToRAIDLinkPHYFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PHY bit errors of the link between expander and RAID card increased too fast. (Generated)"
			::= { hwExpanderEvent 5 }
		hwExpanderToRAIDLinkPHYFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PHY bit errors of the link between expander and RAID card increased too fast. (Cleared)"
			::= { hwExpanderEvent 6 }
		hwExpanderToExpanderLinkPHYFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PHY bit errors of the link between expander and expander increased too fast. (Generated)"
			::= { hwExpanderEvent 7 }
		hwExpanderToExpanderLinkPHYFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The PHY bit errors of the link between expander and expander increased too fast. (Cleared)"
			::= { hwExpanderEvent 8 }
	hwJCChipEvent OBJECT IDENTIFIER ::= {hwServerTRAPObjectV2 57 }
		hwJCChipVMSEFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU-JC VMSE error. (Generated)"
			::= { hwJCChipEvent 1 }
		hwJCChipVMSEFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU-JC VMSE error. (Cleared)"
			::= { hwJCChipEvent 2 }
		hwJCChipOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU JC overheating minor alarm. (Generated)"
			::= { hwJCChipEvent 3 }
		hwJCChipOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU JC overheating minor alarm. (Cleared)"
			::= { hwJCChipEvent 4 }
		hwJCChipOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU JC overheating major alarm. (Generated)"
			::= { hwJCChipEvent 5 }
		hwJCChipOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"CPU JC overheating major alarm. (Cleared)"
			::= { hwJCChipEvent 6 }
		hwJCChipAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU JC temperature. (Generated)"
			::= { hwJCChipEvent 7 }
		hwJCChipAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read CPU JC temperature. (Cleared)"
			::= { hwJCChipEvent 8 }
	hwSCMEvent OBJECT IDENTIFIER ::= {hwServerTRAPObjectV2 58 }
		hwSCMEventMemoryBrdCFGErr NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory board configuration error. (Generated)"
			::= { hwSCMEvent 1 }
		hwSCMEventMemoryBrdCFGErrDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Memory board configuration error. (Cleared)"
			::= { hwSCMEvent 2 }
	hwSDRAIDEvent OBJECT IDENTIFIER ::= {hwServerTRAPObjectV2 59 }
		hwSDRAIDCardFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card RAID controller fault. (Generated)"
			::= { hwSDRAIDEvent 1 }
		hwSDRAIDCardFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"SD card RAID controller fault. (Cleared)"
			::= { hwSDRAIDEvent 2 }
	hwPCIeSwitchEvent OBJECT IDENTIFIER ::= {hwServerTRAPObjectV2 63 }
		hwPCIeSwitchCoreVoltLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch core-volt undervoltage major alarm. (Generated)"
			::= { hwPCIeSwitchEvent 1 }
		hwPCIeSwitchCoreVoltLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch core-volt undervoltage major alarm. (Cleared)"
			::= { hwPCIeSwitchEvent 2 }
		hwPCIeSwitchCoreVoltOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch core-volt overvoltage major alarm. (Generated)"
			::= { hwPCIeSwitchEvent 3 }
		hwPCIeSwitchCoreVoltOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch core-volt overvoltage major alarm. (Cleared)"
			::= { hwPCIeSwitchEvent 4 }
		hwPCIeSwitchCoreVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe switch core voltage. (Generated)"
			::= { hwPCIeSwitchEvent 5 }
		hwPCIeSwitchCoreVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe switch core voltage. (Cleared)"
			::= { hwPCIeSwitchEvent 6 }
		hwPCIeSwitchVDDVoltLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch VDD undervoltage major alarm. (Generated)"
			::= { hwPCIeSwitchEvent 7 }
		hwPCIeSwitchVDDVoltLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch VDD undervoltage major alarm. (Cleared)"
			::= { hwPCIeSwitchEvent 8 }
		hwPCIeSwitchVDDVoltOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch VDD overvoltage major alarm. (Generated)"
			::= { hwPCIeSwitchEvent 9 }
		hwPCIeSwitchVDDVoltOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch VDD overvoltage major alarm. (Cleared)"
			::= { hwPCIeSwitchEvent 10 }
		hwPCIeSwitchVDDVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe switch VDD voltage. (Generated)"
			::= { hwPCIeSwitchEvent 11 }
		hwPCIeSwitchVDDVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe switch VDD voltage. (Cleared)"
			::= { hwPCIeSwitchEvent 12 }
		hwPCIeSwitchInputVoltLowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch input-volt undervoltage major alarm. (Generated)"
			::= { hwPCIeSwitchEvent 13 }
		hwPCIeSwitchInputVoltLowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch input-volt undervoltage major alarm. (Cleared)"
			::= { hwPCIeSwitchEvent 14 }
		hwPCIeSwitchInputVoltOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch input-volt overvoltage major alarm. (Generated)"
			::= { hwPCIeSwitchEvent 15 }
		hwPCIeSwitchInputVoltOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch input-volt overvoltage major alarm. (Cleared)"
			::= { hwPCIeSwitchEvent 16 }
		hwPCIeSwitchInputVoltFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe switch input voltage. (Generated)"
			::= { hwPCIeSwitchEvent 17 }
		hwPCIeSwitchInputVoltFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe switch input voltage. (Cleared)"
			::= { hwPCIeSwitchEvent 18 }
		hwPCIeSwitchOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch overheating minor alarm. (Generated)"
			::= { hwPCIeSwitchEvent 19 }
		hwPCIeSwitchOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch overheating minor alarm. (Cleared)"
			::= { hwPCIeSwitchEvent 20 }
		hwPCIeSwitchOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch overheating major alarm. (Generated)"
			::= { hwPCIeSwitchEvent 21 }
		hwPCIeSwitchOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe switch overheating major alarm. (Cleared)"
			::= { hwPCIeSwitchEvent 22 }
		hwPCIeSwitchAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe switch temperature. (Generated)"
			::= { hwPCIeSwitchEvent 23 }
		hwPCIeSwitchAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read PCIe switch temperature. (Cleared)"
			::= { hwPCIeSwitchEvent 24 }
        hwPCIeSwitchFileFail NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain PCIe Switch update file. (Generated)"
			::= { hwPCIeSwitchEvent 25 }
		hwPCIeSwitchFileFailDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain PCIe Switch update file. (Cleared)"
			::= { hwPCIeSwitchEvent 26 }
        hwPCIeSwitchUpdateFail NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to update PCIe Switch eeprom. (Generated)"
			::= { hwPCIeSwitchEvent 27 }
		hwPCIeSwitchUpdateFailDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to update PCIe Switch eeprom. (Cleared)"
			::= { hwPCIeSwitchEvent 28 }
        hwPCIeSwitchUncorrectableError NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Uncorrectable PCIe Switch error. (Generated)"
			::= { hwPCIeSwitchEvent 29 }
		hwPCIeSwitchUncorrectableErrorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Uncorrectable PCIe Switch error. (Cleared)"
			::= { hwPCIeSwitchEvent 30 }
	hwConnectionBoardEvent OBJECT IDENTIFIER ::= {hwServerTRAPObjectV2 64 }
		hwConnBoardNotProInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Connection board not securely installed. (Generated)"
			::= { hwConnectionBoardEvent 1 }
		hwConnBoardNotProInstalledDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Connection board not securely installed. (Cleared)"
			::= { hwConnectionBoardEvent 2 }
		hwConnBoardAbsent NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Connection board not detected. (Generated)"
			::= { hwConnectionBoardEvent 3 }
		hwConnBoardAbsentDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Connection board not detected. (Cleared)"
			::= { hwConnectionBoardEvent 4 }
		hwConnBoardFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Connection board fault. (Generated)"
			::= { hwConnectionBoardEvent 5 }
		hwConnBoardFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Connection board fault. (Cleared)"
			::= { hwConnectionBoardEvent 6 }
	hwGPUCarrierBoardEvent OBJECT IDENTIFIER ::= {hwServerTRAPObjectV2 65 }
	    hwGPUCarrierBoardlowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board voltage below lower major threshold. (Generated)"
			::= { hwGPUCarrierBoardEvent 1 }
		hwGPUCarrierBoardlowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board voltage below lower major threshold. (Cleared)"
			::= { hwGPUCarrierBoardEvent 2 }
		hwGPUCarrierBoardOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board overvoltage major alarm. (Generated)"
			::= { hwGPUCarrierBoardEvent 3 }
		hwGPUCarrierBoardOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board overvoltage major alarm. (Cleared)"
			::= { hwGPUCarrierBoardEvent 4 }
		hwGPUCarrierBoardAccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the voltage of GPU carrier board.(Generated)"
			::= { hwGPUCarrierBoardEvent 5 }
		hwGPUCarrierBoardAccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the voltage of GPU carrier board.(Cleared)"
			::= { hwGPUCarrierBoardEvent 6 }
		hwGPUCarrierBoardOverTempMinor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board  temperature at detection point exceeds the overtemperature threshold.(Generated)"
			::= { hwGPUCarrierBoardEvent 7 }
		hwGPUCarrierBoardOverTempMinorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board  temperature at detection point exceeds the overtemperature threshold.(Cleared)"
			::= { hwGPUCarrierBoardEvent 8 }
		hwGPUCarrierBoardAccessTempFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the temperature at detection point on the GPU carrier board.(Generated)"
			::= { hwGPUCarrierBoardEvent 9 }
		hwGPUCarrierBoardAccessTempFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the temperature at detection point on the GPU carrier board.(Cleared)"
			::= { hwGPUCarrierBoardEvent 10 }
		hwGPUCarrierBoardClockSignalLost NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board clock signals lost.(Generated)"
			::= { hwGPUCarrierBoardEvent 11 }
		hwGPUCarrierBoardClockSignalLostDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board clock signals lost.(Cleared)"
			::= { hwGPUCarrierBoardEvent 12 }
		hwGPUCarrierBoardCPLDSelfTestFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board CPLD self-check error.(Generated)"
			::= { hwGPUCarrierBoardEvent 13 }
		hwGPUCarrierBoardCPLDSelfTestFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board CPLD self-check error.(Cleared)"
			::= { hwGPUCarrierBoardEvent 14 }
		hwGPUCarrierBoardAccessPowerFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the power of GPU carrier board.(Generated)"
			::= { hwGPUCarrierBoardEvent 15 }
		hwGPUCarrierBoardAccessPowerFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to obtain the power of GPU carrier board.(Cleared)"
			::= { hwGPUCarrierBoardEvent 16 }
		hwGPUCarrierBoardPowerOnFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to power on GPU carrier board.(Generated)"
			::= { hwGPUCarrierBoardEvent 17 }
		hwGPUCarrierBoardPowerOnFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to power on GPU carrier board.(Cleared)"
			::= { hwGPUCarrierBoardEvent 18 }
		hwGPUCarrierBoardInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board installed."
			::= { hwGPUCarrierBoardEvent 19 }
		hwGPUCarrierBoardRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board removed."
			::= { hwGPUCarrierBoardEvent 21 }
		hwGPUCarrierBoardMOSOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The soft-start circuit MOS FET temperature at detection point of GPU carrier board is too high. (Generated)"
			::= { hwGPUCarrierBoardEvent 23 }
		hwGPUCarrierBoardMOSOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The soft-start circuit MOS FET temperature at detection point of GPU carrier board is too high. (Cleared)"
			::= { hwGPUCarrierBoardEvent 24 }
		hwGPUCarrierBoardSoftStartPGAbnormal NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The soft-start circuit power supply at detection point of GPU carrier board is abnormal. (Generated)"
			::= { hwGPUCarrierBoardEvent 25 }
		hwGPUCarrierBoardSoftStartPGAbnormalDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The soft-start circuit power supply at detection point of GPU carrier board is abnormal. (Cleared)"
			::= { hwGPUCarrierBoardEvent 26 }
		hwGPUCarrierBoardGPUThermalOver NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"MOS temperature on GPU carrier board exceeds the protection point. (Generated)"
			::= { hwGPUCarrierBoardEvent 29 }
		hwGPUCarrierBoardGPUThermalOverDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"MOS temperature on GPU carrier board exceeds the protection point. (Cleared)"
			::= { hwGPUCarrierBoardEvent 30 }
	
	    hwGPUCarrierBoardOverTempMajor NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board  temperature at detection point exceeds the overtemperature threshold.(Generated)"
			::= { hwGPUCarrierBoardEvent 31 }
		hwGPUCarrierBoardOverTempMajorDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"GPU carrier board  temperature at detection point exceeds the overtemperature threshold.(Cleared)"
			::= { hwGPUCarrierBoardEvent 32 }
	hwDiskBaseboardEvent OBJECT IDENTIFIER ::= {hwServerTRAPObjectV2 66 }
    		hwDiskDrawerClose NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk drawer closed."
			::= { hwDiskBaseboardEvent 1 }
       		hwDiskDrawerOpen NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Hard disk drawer opened."
			::= { hwDiskBaseboardEvent 3 }
    hwEIUABoardEvent OBJECT IDENTIFIER ::= {hwServerTRAPObjectV2 67 }
	    hwEIUABoardlowerVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"EIUA board voltage below lower major threshold. (Generated)"
			::= { hwEIUABoardEvent 1 }
		hwEIUABoardlowerVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"EIUA board voltage below lower major threshold. (Cleared)"
			::= { hwEIUABoardEvent 2 }
		hwEIUABoardOverVoltage NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"EIUA board overvoltage major alarm. (Generated)"
			::= { hwEIUABoardEvent 3 }
		hwEIUABoardOverVoltageDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"EIUA board overvoltage major alarm. (Cleared)"
			::= { hwEIUABoardEvent 4 }
		hwEIUABoardAccessVoltageFailure NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read EIUA board voltage. (Generated)"
			::= { hwEIUABoardEvent 5 }
		hwEIUABoardAccessVoltageFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to read EIUA board voltage. (Cleared)"
			::= { hwEIUABoardEvent 6 }	
            
    hwLogicaldriveEvent OBJECT IDENTIFIER ::= {hwServerTRAPObjectV2 69 }
		hwLogicalDriveFault NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Logical drive degraded or partially degraded or offline. (Generated)"
			::= { hwLogicaldriveEvent 1 }
		hwLogicalDriveFaultDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Logical drive degraded or partially degraded or offline. (Cleared)"
			::= { hwLogicaldriveEvent 2 }
    hwFanBoardEvent OBJECT IDENTIFIER ::= {hwServerTRAPObjectV2 25 }
		hwFanBoardOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fan backplane power supply over temperature.(Generated)"
			::= { hwFanBoardEvent 1 }
		hwFanBoardOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fan backplane power supply over temperature.(Cleared)"
			::= { hwFanBoardEvent 2 }
		hwFanBoardPowerFailure  NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fan backplane power failure.(Generated)"
			::= { hwFanBoardEvent 3 }
		hwFanBoardPowerFailureDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Fan backplane power failure.(Cleared)"
			::= { hwFanBoardEvent 4 }
    hwPCIeRetimerEvent OBJECT IDENTIFIER ::= {hwServerTRAPObjectV2 70 }
		hwPCIeRetimerUpdateFail NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe retimer upgrade failure."
			::= { hwPCIeRetimerEvent 1 }
		hwPCIeRetimerConfigureFail NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to configure the Retimer. (Generated)"
			::= { hwPCIeRetimerEvent 3 }
		hwPCIeRetimerConfigureFailDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to configure the Retimer. (Cleared)"
			::= { hwPCIeRetimerEvent 4 }
		hwPCIeRetimerLoadFileFail NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe retimer load failure.(Generated)"
			::= { hwPCIeRetimerEvent 5 }
		hwPCIeRetimerLoadFileFailDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PCIe retimer load failure.(Cleared)"
			::= { hwPCIeRetimerEvent 6 }        
    hwBMAEvent OBJECT IDENTIFIER ::= {hwServerTRAPObjectV2 74 }
		hwBMAForwardFailed NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to create a forward mapping table on the iBMA. (Generated)"
			::= { hwBMAEvent 1 }
		hwBMAForwardFailedDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to create a forward mapping table on the iBMA. (Cleared)"
			::= { hwBMAEvent 2 }	
	hwPWRBoardEvent OBJECT IDENTIFIER ::= {hwServerTRAPObjectV2 26 }
		hwPWRBoardOverTemp NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PSU backplane power supply overtemperature.(Generated)"
			::= { hwPWRBoardEvent 1 }
		hwPWRBoardOverTempDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"PSU backplane power supply overtemperature.(Cleared)"
			::= { hwPWRBoardEvent 2 }
	hwRepeaterPCIeEvent OBJECT IDENTIFIER ::= {hwServerTRAPObjectV2 71 }
		hwRepeaterPCIeConfigureFail NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to configure the Repeater. (Generated)"
			::= { hwRepeaterPCIeEvent 1 }
		hwRepeaterPCIeConfigureFailDeassert NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"Failed to configure the Repeater. (Cleared)"
			::= { hwRepeaterPCIeEvent 2 }
	hwPassThroughCardEvent OBJECT IDENTIFIER ::= {hwServerTRAPObjectV2 68 }
		hwPassThroughCardInstalled NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The pass-through card installed."
			::= { hwPassThroughCardEvent 1 }
		hwPassThroughCardRemoved NOTIFICATION-TYPE
			OBJECTS { hwTrapSeq, hwTrapSensorName, hwTrapEvent, hwTrapSeverity, hwTrapEventCode, hwTrapEventData2, hwTrapEventData3, hwTrapServerIdentity, hwTrapLocation, hwTrapTime }
			STATUS current
			DESCRIPTION
				"The pass-through card removed."
			::= { hwPassThroughCardEvent 3 }
--		****** hwServerTRAPObjectV2 End ******

--    ****** remoteManagement Information *******************************
  
		remoteManagement OBJECT IDENTIFIER ::= { hwiBMC 28 }           
			

		powerOnControl OBJECT-TYPE
			SYNTAX DisplayString
			MAX-ACCESS read-write
			STATUS current
			DESCRIPTION
				"The powerOnControl format: IP,PORT,ENABLE(eg 192.168.1.1,6999,1), maxlength is 255 characters."
			::= { remoteManagement 1 }
			
			
--    ****** SDCard Information *******************************
  
		sdCardProperty OBJECT IDENTIFIER ::= { hwiBMC 32 }
		

		sdCardControllerManufacturer OBJECT-TYPE
			SYNTAX DisplayString 
			MAX-ACCESS read-only
			STATUS current
			DESCRIPTION
				"Information about SD card controller manufacturer."
			::= { sdCardProperty 1 }    
			
		sdCardControllerVersion OBJECT-TYPE
			SYNTAX DisplayString 
			MAX-ACCESS read-only
			STATUS current
			DESCRIPTION
				"Information about SD card controller version."
			::= { sdCardProperty 2 }    

		sdCardEntireStatus OBJECT-TYPE
			SYNTAX INTEGER 
				{
				ok(1),
				minor(2),
				major(3),
				critical(4),
				absence(5),
				unknown(6)
				}
			MAX-ACCESS read-only
			STATUS current
			DESCRIPTION
				"Information about all sdcard health status."
			::= { sdCardProperty 3 }   

		sdCardDescriptionTable OBJECT-TYPE
			SYNTAX SEQUENCE OF SdCardDescriptionEntry 
			MAX-ACCESS not-accessible
			STATUS current
			DESCRIPTION
				"A table containing the sd card."
			::= { sdCardProperty 50 }
        
                sdCardDescriptionEntry OBJECT-TYPE
			SYNTAX SdCardDescriptionEntry 
			MAX-ACCESS not-accessible
			STATUS current
			DESCRIPTION
				"Information about sd card."
			INDEX { sdCardIndex }
			::= { sdCardDescriptionTable 1 }
		
		SdCardDescriptionEntry ::=
			SEQUENCE {
				sdCardIndex
					INTEGER, 
				sdCardPresence
					INTEGER,
				sdCardStatus
					INTEGER,
				sdCardCapacity 
					INTEGER, 
				sdCardManufacturer
					DisplayString,
				sdCardSN
					DisplayString	
				}
				 

		sdCardIndex OBJECT-TYPE	
			SYNTAX INTEGER
			MAX-ACCESS not-accessible
			STATUS current
			DESCRIPTION
				"Information about sd card index."
			::= { sdCardDescriptionEntry 1 } 
			

		sdCardPresence OBJECT-TYPE
			SYNTAX INTEGER
				{
				absence(1),
				presence(2),
				unknown(3)
				}
			MAX-ACCESS read-only
			STATUS current
			DESCRIPTION
				"Information about sd card presence."
			::= { sdCardDescriptionEntry 2 }


		sdCardStatus OBJECT-TYPE
			SYNTAX INTEGER 
				{
				ok(1),
				minor(2),
				major(3),
				critical(4),
				absence(5),
				unknown(6)
				}
			MAX-ACCESS read-only
			STATUS current
			DESCRIPTION
				"Information about sd card health."
			::= { sdCardDescriptionEntry 3 }  

		sdCardCapacity OBJECT-TYPE	
			SYNTAX INTEGER
			MAX-ACCESS read-only
			STATUS current
			DESCRIPTION
				"sd card capacity(MB)."
			::= { sdCardDescriptionEntry 4 } 

		
		sdCardManufacturer OBJECT-TYPE	
			SYNTAX DisplayString
			MAX-ACCESS read-only
			STATUS current
			DESCRIPTION
				"sd card manufacturer."
			::= { sdCardDescriptionEntry 5 } 

		
		sdCardSN OBJECT-TYPE	
			SYNTAX DisplayString
			MAX-ACCESS read-only
			STATUS current
			DESCRIPTION
				"sd card sn."
			::= { sdCardDescriptionEntry 6 } 				

			
--    ****** securityModuleProperty Information *******************************
  
		securityModuleProperty OBJECT IDENTIFIER ::= { hwiBMC 33 }
			

		presence OBJECT-TYPE
			SYNTAX INTEGER
				{
				absence(1),
				presence(2),
				unknown(3)
				}
			MAX-ACCESS read-only
			STATUS current
			DESCRIPTION
				"Presence of security module."
			::= { securityModuleProperty 1 }
			

		specificationType OBJECT-TYPE
			SYNTAX DisplayString
			MAX-ACCESS read-only
			STATUS current
			DESCRIPTION
				"Specification type of security module."
			::= { securityModuleProperty 2 } 
			

		specificationVersion OBJECT-TYPE
			SYNTAX DisplayString
			MAX-ACCESS read-only
			STATUS current
			DESCRIPTION
				"Specification version of security module."
			::= { securityModuleProperty 3 }	
			

		manufacturerName OBJECT-TYPE
			SYNTAX DisplayString
			MAX-ACCESS read-only
			STATUS current
			DESCRIPTION
				"Manufacturer name of security module."
			::= { securityModuleProperty 4 }
			

		manufacturerVersion OBJECT-TYPE
			SYNTAX DisplayString
			MAX-ACCESS read-only
			STATUS current
			DESCRIPTION
				"Manufacturer firmware version of security module."
			::= { securityModuleProperty 5 }
--    ****** fileTransfer Information *******************************
    fileTransfer OBJECT IDENTIFIER ::= { hwiBMC 35 }
	
	fileTransferUrl OBJECT-TYPE
			SYNTAX DisplayString
			MAX-ACCESS read-write
			STATUS current
			DESCRIPTION
				"The file transfer URL format is: <download/upload><ID><protocol://[username:password@]IP[:port]/directory/filename> 
				 The maximum length of the URL is 1024 bytes.
				 The parameters in the URL are described as follows:
				 	 The download means download file to BMC.
				 	 The upload means upload file to the destination server. 
				 	 The ID is the file ID, ranging from 0 to 255.
				 	 The supported protocols include https, sftp, cifs, scp, and nfs.
				 	 The username and password are those of the destination server. 
				 	 The IP can be set to an IPv4/IPv6 address or a domain name.
				 	 The directory and filename are those on the destination server.
				 Example URLs are as follows: 
				 	 download;0;https://root:test1234@192.168.2.13:443/data/display0.ini
				 	 upload;1;sftp://root:test1234@[2001::178]/home/options0.ini
				 The URL can contain only letters, digits, and special characters. The directory or file name cannot contain @."
			::= { fileTransfer 1 }                                                                                                                           
	
	fileTransferState OBJECT-TYPE
			SYNTAX INTEGER
			MAX-ACCESS read-only
			STATUS current
			DESCRIPTION
				"Information about file transfer state.
				the value defined as:
				  -1  : unknown error,
				  -101: download unavailable,
				  -102: file name too long,
				  -103: failed to obtain the file length, or the file length out of MAXlength or memory,
				  -104: set file update flag error,
				  -105: libcurl run error,
				  -106: upload unavailable,
				  -107: upload file unavailable,
				  -108: protocol not supported,
				  -109: url format error,
				  [0,100]:represents transfer progress in percentage while file being transfered."
			::= { fileTransfer 2 } 
      			                                                     
		                                       
--    ****** RAID Controller Information *******************************
  
		raidControllerProperty OBJECT IDENTIFIER ::= { hwiBMC 36 } 

		raidControllerDescriptionTable OBJECT-TYPE
			SYNTAX SEQUENCE OF RAIDControllerDescriptionEntry 
			MAX-ACCESS not-accessible
			STATUS current
			DESCRIPTION
				"A table containing the RAID controller."
			::= { raidControllerProperty 50 }
        
                raidControllerDescriptionEntry OBJECT-TYPE
			SYNTAX RAIDControllerDescriptionEntry 
			MAX-ACCESS not-accessible
			STATUS current
			DESCRIPTION
				"Information about RAID controller."
			INDEX { raidControllerIndex }
			::= { raidControllerDescriptionTable 1 }
		
		RAIDControllerDescriptionEntry ::=
			SEQUENCE {
				raidControllerIndex
					INTEGER, 
				raidControllerName
					DisplayString,
				raidControllerType
					DisplayString,
				raidControllerComponentName
					DisplayString, 
				raidControllerSupportOOBManagement
					INTEGER,
				raidControllerMode
					INTEGER,
				raidControllerHealthStatus
					INTEGER,	
				raidControllerFwVersion
					DisplayString,	
				raidControllerNVDataVersion
					DisplayString,
				raidControllerMemorySizeInMB
					INTEGER,
				raidControllerDeviceInterface
					INTEGER,
				raidControllerSASAddress
					DisplayString,
				raidControllerCachePinned
					INTEGER,
				raidControllerMaintainPDFailHistory
					INTEGER,
				raidControllerDDREccCount
					INTEGER,
				raidControllerBBUPresence
					INTEGER,
				raidControllerBBUType
					DisplayString,
				raidControllerBBUHealthStatus
					INTEGER,
				raidControllerMinStripSupportInBytes
					INTEGER,
				raidControllerMaxStripSupportInBytes
					INTEGER,
				raidControllerCopybackEnable
					INTEGER,
				raidControllerSMARTerCopybackEnable
					INTEGER,
				raidControllerJBODEnable
					INTEGER,					
				raidControllerRestoreSettings
					INTEGER,	
				raidControllerCreateLD
					DisplayString,	
				raidControllerAddLD
					DisplayString,						
				raidControllerDriverName
					DisplayString,
				raidControllerDriverVersion
					DisplayString,
				raidControllerSupportedRAIDLevels
					DisplayString
				}											   

		raidControllerIndex OBJECT-TYPE
			SYNTAX INTEGER
			MAX-ACCESS not-accessible
			STATUS current
			DESCRIPTION
				"Information about RAID controller index."
			::= { raidControllerDescriptionEntry 1 }

		raidControllerName OBJECT-TYPE
			SYNTAX DisplayString
			MAX-ACCESS read-only
			STATUS current
			DESCRIPTION
				"Information about RAID controller name."
			::= { raidControllerDescriptionEntry 2 }				
											   											   
		raidControllerType OBJECT-TYPE
			SYNTAX DisplayString
			MAX-ACCESS read-only
			STATUS current
			DESCRIPTION
				"Information about RAID controller type."
			::= { raidControllerDescriptionEntry 3 }

		raidControllerComponentName OBJECT-TYPE
			SYNTAX DisplayString
			MAX-ACCESS read-only
			STATUS current
			DESCRIPTION
				"Information about RAID controller component name."
			::= { raidControllerDescriptionEntry 4 }

		raidControllerSupportOOBManagement OBJECT-TYPE
			SYNTAX INTEGER
				{
				no(1),
				yes(2)
				}
			MAX-ACCESS read-only
			STATUS current
			DESCRIPTION
				"Information about RAID controller if support OOB management.
				1: No
				2: Yes"
			::= { raidControllerDescriptionEntry 5 }
			
		raidControllerMode OBJECT-TYPE
			SYNTAX INTEGER
				{
				raid(1),
				hba(2),
				jbod(3),
				unknown(255)
				}
			MAX-ACCESS read-only
			STATUS current
			DESCRIPTION
				"Information about RAID controller mode.
				1: RAID
				2: HBA
				3: JBOD
				255: Unknown"
			::= { raidControllerDescriptionEntry 6 }

		raidControllerHealthStatus OBJECT-TYPE
			SYNTAX INTEGER
				{
				ok(0),
				unknown(65535)
				}			
			MAX-ACCESS read-only
			STATUS current
			DESCRIPTION
				"Information about RAID controller health status.
				bit0: 1- memory correctable error
				bit1: 1- memory uncorrectable error
				bit2: 1- memory ECC error reached limit
				bit3: 1- NVRAM uncorrectable error
				other: reserved"
			::= { raidControllerDescriptionEntry 7 }

		raidControllerFwVersion OBJECT-TYPE
			SYNTAX DisplayString
			MAX-ACCESS read-only
			STATUS current
			DESCRIPTION
				"Information about RAID controller firmware version."
			::= { raidControllerDescriptionEntry 8 }
		
		raidControllerNVDataVersion OBJECT-TYPE
			SYNTAX DisplayString
			MAX-ACCESS read-only
			STATUS current
			DESCRIPTION
				"Information about RAID controller NVData version."
			::= { raidControllerDescriptionEntry 9 }

		raidControllerMemorySizeInMB OBJECT-TYPE
			SYNTAX INTEGER
				{
				unknown(65535)
				}			
			MAX-ACCESS read-only
			STATUS current
			DESCRIPTION
				"Information about RAID controller memory size (MB)."
			::= { raidControllerDescriptionEntry 10 }			

		raidControllerDeviceInterface OBJECT-TYPE
			SYNTAX INTEGER
				{
				spi(1),
				sas-3G(2),
				sata-1-5G(3),
				sata-3G(4),
				sas-6G(5),
				sas-12G(6),
				unknown(255)
				}			
			MAX-ACCESS read-only
			STATUS current
			DESCRIPTION
				"Information about RAID controller device interface type.
				1: SPI
				2: SAS-3G
				3: SATA-1.5G
				4: SATA-3G
				5: SAS-6G
				6: SAS-12G
				255: Unknown"
			::= { raidControllerDescriptionEntry 11 }				

		raidControllerSASAddress OBJECT-TYPE
			SYNTAX DisplayString
			MAX-ACCESS read-only
			STATUS current
			DESCRIPTION
				"Information about RAID controller SAS address."
			::= { raidControllerDescriptionEntry 12 }

		raidControllerCachePinned OBJECT-TYPE
			SYNTAX INTEGER
				{
				no(1),
				yes(2),
				unknown(255)
				}			
			MAX-ACCESS read-only
			STATUS current
			DESCRIPTION
				"Information about RAID controller if cache is pinned.
				1: No
				2: Yes
				255: Unknown"
			::= { raidControllerDescriptionEntry 13 }				
			
		raidControllerMaintainPDFailHistory OBJECT-TYPE
			SYNTAX INTEGER
				{
				no(1),
				yes(2),
				unknown(255)
				}			
			MAX-ACCESS read-only
			STATUS current
			DESCRIPTION
				"Information about RAID controller if maintain PD fail history.
				1: No
				2: Yes
				255: Unknown"
			::= { raidControllerDescriptionEntry 14 }

		raidControllerDDREccCount OBJECT-TYPE
			SYNTAX INTEGER
				{
				unknown(65535)
				}			
			MAX-ACCESS read-only
			STATUS current
			DESCRIPTION
				"Information about RAID controller DDR ECC count."
			::= { raidControllerDescriptionEntry 15 }

		raidControllerBBUPresence OBJECT-TYPE
			SYNTAX INTEGER
				{
				absent(1),
				present(2),
				unknown(255)
				}			
			MAX-ACCESS read-only
			STATUS current
			DESCRIPTION
				"Information about RAID controller's BBU presence.
				1: Absent
				2: Present
				255: Unknown"
			::= { raidControllerDescriptionEntry 16 }

		raidControllerBBUType OBJECT-TYPE
			SYNTAX DisplayString
			MAX-ACCESS read-only
			STATUS current
			DESCRIPTION
				"Information about RAID controller' BBU type."
			::= { raidControllerDescriptionEntry 17 }			
			
		raidControllerBBUHealthStatus OBJECT-TYPE
			SYNTAX INTEGER			
			{
			ok(0)
			}
			MAX-ACCESS read-only
			STATUS current
			DESCRIPTION
				"Information about RAID controller's BBU health status.
				bit0: 1 - voltage is low
				bit1: 1 - need replace pack
				bit2: 1 - learn cycle failed
				bit3: 1 - learn cycle timeout
				bit4: 1 - pack is about to fail
				bit5: 1 - remaining capacity low
				bit6: 1 - no space for cache offload
				others: reserved"
			::= { raidControllerDescriptionEntry 18 }
			
		raidControllerMinStripSupportInBytes OBJECT-TYPE
			SYNTAX INTEGER
			{
				unknown(-1)
			}			
			MAX-ACCESS read-only
			STATUS current
			DESCRIPTION
				"Information about the minimum strip size that RAID controller support."
			::= { raidControllerDescriptionEntry 19 }
			
		raidControllerMaxStripSupportInBytes OBJECT-TYPE
			SYNTAX INTEGER
			{
				unknown(-1)
			}			
			MAX-ACCESS read-only
			STATUS current
			DESCRIPTION
				"Information about the maximum strip size that RAID controller support."
			::= { raidControllerDescriptionEntry 20 }			
			
		raidControllerCopybackEnable OBJECT-TYPE
			SYNTAX INTEGER
				{
				unknown(1),
				disabled(2),
				enabled(3)
				}			
			MAX-ACCESS read-write
			STATUS current
			DESCRIPTION
				"Information about the copyback state of RAID controller.
				1: Unknown (read only)
				2: Disabled
				3: Enabled"
			::= { raidControllerDescriptionEntry 21 }			
			
		raidControllerSMARTerCopybackEnable OBJECT-TYPE
			SYNTAX INTEGER
				{
				unknown(1),
				disabled(2),
				enabled(3)
				}			
			MAX-ACCESS read-write
			STATUS current
			DESCRIPTION
				"Information about the copyback state on SMART error of RAID controller.
				1: Unknown (read only)
				2: Disabled
				3: Enabled
				
				Note: Set action is available only when raidControllerCopybackEnable = Enabled."
			::= { raidControllerDescriptionEntry 22 }			
			                                                 
		raidControllerJBODEnable OBJECT-TYPE
			SYNTAX INTEGER
				{
				unknown(1),
				disabled(2),
				enabled(3)
				}			
			MAX-ACCESS read-write
			STATUS current
			DESCRIPTION
				"Information about the JBOD state of RAID controller.
				1: Unknown (read only)
				2: Disabled
				3: Enabled"
			::= { raidControllerDescriptionEntry 23 }			
			
		raidControllerRestoreSettings OBJECT-TYPE
			SYNTAX INTEGER			
			MAX-ACCESS read-write
			STATUS current
			DESCRIPTION
				"Restore RAID controller settings (write only). The argument is:
				1: Restore RAID controller settings.
				others: invalid"
			::= { raidControllerDescriptionEntry 24 }			
			
		raidControllerCreateLD OBJECT-TYPE
			SYNTAX DisplayString			
			MAX-ACCESS read-write
			STATUS current
			DESCRIPTION
				"Create new logical drive on this RAID controller. The arguments are seperated by semicolons;
				The arguments format is <option1>=<argument>;<option2>=<argument>;...;<optionN>=<argument>;
				example: 
					rl=r1;pd=1,2;name=example;size=100.375g;ss=256k;sc=1;rp=ra;wp=wb;iop=cio;ap=rw;dcp=enabled;init=quick;
				or  
					rl=r50;pd=1,2,3,4,5,6,7,8,9;name=example;size=500g;ss=1M;sc=3;rp=ra;wp=wb;iop=cio;ap=rw;dcp=enabled;init=quick;

				Options and arguments:	
				rl=<RAID level>                          The RAID level of logical drive. It is mandatory. When 'cachecade=1' is specified, RAID level 0/1 is valid.
					r0: RAID0
					r1: RAID1
					r5: RAID5
					r6: RAID6
					r10: RAID10
					r50: RAID50
					r60: RAID60
				pd=<PD IDs>                              The physical drives IDs which participate this logical drive. It is mandatory. 
				name=<Logical drive name>                The name of logical drive. The maximum is 15 printable ASCII characters except ';'. It is optional.
				size=<Logical drive size>                The size of logical drive and unit can be 'm'(megabytes),'g'(gigabytes), or 't'(terabytes). 
				                                         It is optional and not necessary when 'cachecade=1' is specified.
				ss=<Logical drive strip size>            The strip size of logical drive. The valid values are 64k,128k,256k,512k,1M. 
				                                         It is optional and not necessary when 'cachecade=1' is specified.
				sc=<Span count>                          The span count of logical drive. The default is 1 when RAID level is RAID0/1/5/6 and 2 when RAID level is RAID10/50/60. 
				                                         It is optional and not necessary when 'cachecade=1' is specified.
				rp=<Read Policy>                         The read policy of logical drive. It is optional and not necessary when 'cachecade=1' is specified.
					ra: Read Ahead
					nra: No Read Ahead
				wp=<Write Policy>                        The write policy of logical drive. It is optional.
					wt: Write Through
					wbwithbbu: Write Back with BBU
					wb: Write Back
				iop=<IO Policy>                          The IO policy of logical drive. It is optional and not necessary when 'cachecade=1' is specified.
					cio: Cached IO
					dio: Direct IO
				ap=<Access Policy>                       The access policy of logical drive. It is optional and not necessary when 'cachecade=1' is specified.
					rw: Read Write
					ro: Read only
					blocked: Blocked
				dcp=<Disk Cache Policy>                  The disk cache policy of logical drive. It is optional and not necessary when 'cachecade=1' is specified.
					enabled: Enable disk cache
					disabled: Disable disk cache
					default: Unchanged(Disk's default)
				init=<Init Type>                         The initialization type of logical drive. It is optional and not necessary when 'cachecade=1' is specified.
					no: No init
					quick: Quick init
					full: Full init
				cachecade=1                              Logical drive is used for secondary cache. It is optional. It must be supported by RAID controller first.
				
				Note: Character ';' is not valid for logical drive name string because it is used as separator."
			::= { raidControllerDescriptionEntry 25 }			
			
		raidControllerAddLD OBJECT-TYPE
			SYNTAX DisplayString			
			MAX-ACCESS read-write
			STATUS current
			DESCRIPTION
				"Add logical drive on array on this RAID controller. The arguments are seperated by semicolons;
				The arguments format is <option1>=<argument>;<option2>=<argument>;...;<optionN>=<argument>;
				example: 
					array=1;name=example;size=100.375g;ss=512k;rp=ra;wp=wb;iop=cio;ap=rw;dcp=enabled;init=quick;

				Options and arguments:	
				array=<Array ID>                          The array on which the logical drive will be added. It is mandatory.
				name=<Logical drive name>                 The name of logical drive and maximum is 15 printable ASCII characters except ';'. It is optional.
				size=<Logical drive size>                 The size of logical drive and unit can be 'm'(megabytes),'g'(gigabytes), or 't'(terabytes). It is optional.
				ss=<Logical drive strip size>             The strip size of logical drive. The valid values are 64k,128k,256k,512k,1M. It is optional.
				rp=<Read Policy>                          The read policy of logical drive. It is optional.
					ra: Read Ahead
					nra: No Read Ahead
				wp=<Write Policy>                         The write policy of logical drive. It is optional.
					wt: Write Through
					wbwithbbu: Write Back with BBU
					wb: Write Back
				iop=<IO Policy>                           The IO policy of logical drive. It is optional.
					cio: Cached IO
					dio: Direct IO
				ap=<Access Policy>                        The access policy of logical drive. It is optional.
					rw: Read Write
					ro: Read only
					blocked: Blocked
				dcp=<Disk Cache Policy>                   The disk cache policy of logical drive. It is optional.
					enabled: Enable disk cache
					disabled: Disable disk cache
					default: Unchanged(Disk's default)
				init=<Init Type>                          The initialization type of logical drive. It is optional.
					no: No init
					quick: Quick init
					full: Full init
					
				Note: Character ';' is not valid for logical drive name string because it is used as separator."
			::= { raidControllerDescriptionEntry 26 }			

		raidControllerDriverName OBJECT-TYPE
			SYNTAX DisplayString
			MAX-ACCESS read-only
			STATUS current
			DESCRIPTION
				"Information about RAID controller driver name."
			::= { raidControllerDescriptionEntry 27 }

		raidControllerDriverVersion OBJECT-TYPE
			SYNTAX DisplayString
			MAX-ACCESS read-only
			STATUS current
			DESCRIPTION
				"Information about RAID controller driver version"
			::= { raidControllerDescriptionEntry 28 }
		
		raidControllerSupportedRAIDLevels OBJECT-TYPE
			SYNTAX DisplayString
			MAX-ACCESS read-only
			STATUS current
			DESCRIPTION
				"Information about RAID controller supported levels."
			::= { raidControllerDescriptionEntry 29 }
			
--  ****************** Logical Drive information **********************

		logicalDriveProperty OBJECT IDENTIFIER ::= { hwiBMC 37 } 

		logicalDriveDescriptionTable OBJECT-TYPE
			SYNTAX SEQUENCE OF LogicalDriveDescriptionEntry 
			MAX-ACCESS not-accessible
			STATUS current
			DESCRIPTION
				"A table containing the logical drive created by RAID controller."
			::= { logicalDriveProperty 50 }
        
                logicalDriveDescriptionEntry OBJECT-TYPE
			SYNTAX LogicalDriveDescriptionEntry 
			MAX-ACCESS not-accessible
			STATUS current
			DESCRIPTION
				"Information about logical drive."
			INDEX { logicalDriveRAIDControllerIndex, logicalDriveIndex }
			::= { logicalDriveDescriptionTable 1 }
		
		LogicalDriveDescriptionEntry ::=
			SEQUENCE {
				logicalDriveRAIDControllerIndex
					INTEGER,
				logicalDriveIndex
					INTEGER,					
				logicalDriveRAIDLevel
					DisplayString,
				logicalDriveState
					INTEGER,
				logicalDriveDefaultReadPolicy
					INTEGER, 
				logicalDriveDefaultWritePolicy
					INTEGER,
				logicalDriveDefaultIOPolicy
					INTEGER,
				logicalDriveCurrentReadPolicy
					INTEGER,	
				logicalDriveCurrentWritePolicy
					INTEGER,	
				logicalDriveCurrentIOPolicy
					INTEGER,
				logicalDriveSpanDepth
					INTEGER,
				logicalDriveNumDrivePerSpan
					INTEGER,
				logicalDriveStripeSizeInBytes
					INTEGER,
				logicalDriveStripeSizeInMB
					INTEGER,					
				logicalDriveSizeInMB
					INTEGER,
				logicalDriveDiskCachePolicy
					INTEGER,
				logicalDriveConsistencyCheckStatus
					INTEGER,
				logicalDriveBootable
					INTEGER,
				logicalDriveName
					DisplayString,
				logicalDriveAccessPolicy
					INTEGER,
				logicalDriveInitState
					INTEGER,	
				logicalDriveBGIEnable
					INTEGER,	
				logicalDriveIsSSCD
					INTEGER,	
				logicalDriveSSCDCachingEnable
					INTEGER,	
				logicalDriveAssociatedLDs
					DisplayString,
				logicalDriveDedicatedSparePD
					DisplayString,	
				logicalDriveDelete
					INTEGER,					
				logicalDriveOSLetter
					DisplayString					
				}											   

		logicalDriveRAIDControllerIndex OBJECT-TYPE
			SYNTAX INTEGER
			MAX-ACCESS not-accessible
			STATUS current
			DESCRIPTION
				"Information about RAID controller index to which this logical drive belongs."
			::= { logicalDriveDescriptionEntry 1 }			

		logicalDriveIndex OBJECT-TYPE
			SYNTAX INTEGER
			MAX-ACCESS not-accessible
			STATUS current
			DESCRIPTION
				"Information about logical drive index in current RAID controller."
			::= { logicalDriveDescriptionEntry 2 }			
			
		logicalDriveRAIDLevel OBJECT-TYPE
			SYNTAX DisplayString			
			MAX-ACCESS read-only
			STATUS current
			DESCRIPTION
				"Information about logical drive RAID level."
			::= { logicalDriveDescriptionEntry 3 }				
											   											   
		logicalDriveState OBJECT-TYPE
			SYNTAX INTEGER
			{
				offline(1),
				partial-degraded(2),
				degraded(3),
				optimal(4),
				unknown(255)
			}
			MAX-ACCESS read-only
			STATUS current
			DESCRIPTION
				"Information about logical drive state.
				1: Offline
				2: Partial degraded
				3: Degraded
				4: Optimal
				255: Unknown"
			::= { logicalDriveDescriptionEntry 4 }

		logicalDriveDefaultReadPolicy OBJECT-TYPE
			SYNTAX INTEGER
			{
				no-read-ahead(1),
				read-ahead(2),
				unknown(255)
			}
			MAX-ACCESS read-write
			STATUS current
			DESCRIPTION
				"Information about logical drive default read policy.
				1: No read ahead
				2: Read ahead
				255: Unknown (read only)
				
				Note: Set action is not available when logical drive is used for secondary cache(logicalDriveIsSSCD = Yes)."
			::= { logicalDriveDescriptionEntry 5 }

		logicalDriveDefaultWritePolicy OBJECT-TYPE
			SYNTAX INTEGER
			{
				write-through(1),
				write-back-with-bbu(2),
				write-back(3),
				unknown(255)
			}
			MAX-ACCESS read-write
			STATUS current
			DESCRIPTION
				"Information about logical drive default write policy.
				1: Write through
				2: Write back with BBU
				3: Write back
				   This option value is not settable when logical drive is used for secondary cache(logicalDriveIsSSCD = Yes).
				255: Unknown (read only)"
			::= { logicalDriveDescriptionEntry 6 }
			
		logicalDriveDefaultIOPolicy OBJECT-TYPE
			SYNTAX INTEGER
			{
				cached-IO(1),
				direct-IO(2),
				unknown(255)
			}
			MAX-ACCESS read-write
			STATUS current
			DESCRIPTION
				"Information about logical drive default IO policy.
				1: Cached IO
				2: Direct IO
				255: Unknown (read only)
				
				Note: Set action is not available when logical drive is used for secondary cache(logicalDriveIsSSCD = Yes)."
			::= { logicalDriveDescriptionEntry 7 }

		logicalDriveCurrentReadPolicy OBJECT-TYPE
			SYNTAX INTEGER
			{
				no-read-ahead(1),
				read-ahead(2),
				unknown(255)
			}			
			MAX-ACCESS read-only
			STATUS current
			DESCRIPTION
				"Information about logical drive current read policy.
				1: No read ahead
				2: Read ahead
				255: Unknown"
			::= { logicalDriveDescriptionEntry 8 }

		logicalDriveCurrentWritePolicy OBJECT-TYPE
			SYNTAX INTEGER
			{
				write-through(1),
				write-back-with-bbu(2),
				write-back(3),
				unknown(255)
			}
			MAX-ACCESS read-only
			STATUS current
			DESCRIPTION
				"Information about logical drive current write policy.
				1: Write Through
				2: Write Back with BBU
				3: Write Back
				255: Unknown"
			::= { logicalDriveDescriptionEntry 9 }
		
		logicalDriveCurrentIOPolicy OBJECT-TYPE
			SYNTAX INTEGER
			{
				cached-IO(1),
				direct-IO(2),
				unknown(255)
			}
			MAX-ACCESS read-only
			STATUS current
			DESCRIPTION
				"Information about logical drive current IO policy.
				1: Cached IO
				2: Direct IO
				255: Unknown"
			::= { logicalDriveDescriptionEntry 10 }

		logicalDriveSpanDepth OBJECT-TYPE
			SYNTAX INTEGER
			{
				unknown(255)
			}			
			MAX-ACCESS read-only
			STATUS current
			DESCRIPTION
				"Information about logical drive span depth."
			::= { logicalDriveDescriptionEntry 11 }			

		logicalDriveNumDrivePerSpan OBJECT-TYPE
			SYNTAX INTEGER
			{
				unknown(255)
			}			
			MAX-ACCESS read-only
			STATUS current
			DESCRIPTION
				"Information about logical drive number of drives per span."
			::= { logicalDriveDescriptionEntry 12 }				

		logicalDriveStripeSizeInBytes OBJECT-TYPE
			SYNTAX INTEGER
			{			
				unknown(4294967295)
			}
			MAX-ACCESS read-only
			STATUS current
			DESCRIPTION
				"Information about logical drive stripe size in bytes."
			::= { logicalDriveDescriptionEntry 13 }
			
		logicalDriveStripeSizeInMB OBJECT-TYPE
			SYNTAX INTEGER
			{			
				unknown(4294967295)
			}
			MAX-ACCESS read-only
			STATUS current
			DESCRIPTION
				"Information about logical drive stripe size in mega-bytes."
			::= { logicalDriveDescriptionEntry 14 }			
			

		logicalDriveSizeInMB OBJECT-TYPE
			SYNTAX INTEGER
			{
				unknown(4294967295)
			}			
			MAX-ACCESS read-only
			STATUS current
			DESCRIPTION
				"Information about logical drive size (MB)."
			::= { logicalDriveDescriptionEntry 15 }				
			
		logicalDriveDiskCachePolicy OBJECT-TYPE
			SYNTAX INTEGER
			{
				disk-default(1),
				enabled(2),
				disabled(3),
				unknown(255)
			}			
			MAX-ACCESS read-write
			STATUS current
			DESCRIPTION
				"Information about logical drive disk cache policy.
				1: Disk's default
				2: Enabled
				3: Disabled
				255: Unknown (read only)
				
				Note: Set action is not available when logical drive's participated physical drives are SSD."
			::= { logicalDriveDescriptionEntry 16 }

		logicalDriveConsistencyCheckStatus OBJECT-TYPE
			SYNTAX INTEGER
			{
				stopped(1),
				in-progress(2),
				unknown(255)
			}			
			MAX-ACCESS read-only
			STATUS current
			DESCRIPTION
				"Information about logical drive consistency check status.
				1: Stopped
				2: In-progress
				255: Unknown"
			::= { logicalDriveDescriptionEntry 17 }

		logicalDriveBootable OBJECT-TYPE
			SYNTAX INTEGER
			{
				no(1),
				yes(2),
				unknown(255)
			}			
			MAX-ACCESS read-write
			STATUS current
			DESCRIPTION
				"Information about logical drive if it is bootable.
				1: No (read only)
				2: Yes
				255: Unknown (read only)
				
				Note: 1. CacheCade logical drive can't be set as bootable drive.
				      2. Noraml logical drive(not cachecade) during offline state can be set bootable successfully, but readback value of logicalDriveBootable
				         is still 'No' unless change the logical drive state to online."
			::= { logicalDriveDescriptionEntry 18 }
		
		logicalDriveName OBJECT-TYPE
			SYNTAX DisplayString			
			MAX-ACCESS read-write
			STATUS current
			DESCRIPTION
				"Information about logical drive name. The maximum is 15 printable ASCII characters."
			::= { logicalDriveDescriptionEntry 19 }		
		
		logicalDriveAccessPolicy OBJECT-TYPE
			SYNTAX INTEGER
			{
				unknown(1),			
				read-write(2),
				read-only(3),
				blocked(4),
				hidden(5)
			}			
			MAX-ACCESS read-write
			STATUS current
			DESCRIPTION
				"Information about logical drive access policy.
				1: Unknown (read only)
				2: Read Write
				3: Read Only
				4: Blocked
				5: Hidden (read only)
				
				Note: Set action is not available when logical drive is used for secondary cache(logicalDriveIsSSCD = Yes)."
			::= { logicalDriveDescriptionEntry 20 }		

		logicalDriveInitState OBJECT-TYPE
			SYNTAX INTEGER
			{
				unknown(1),			
				no-init(2),
				quick-init(3),
				full-init(4)
			}			
			MAX-ACCESS read-only
			STATUS current
			DESCRIPTION
				"Information about logical drive init state.
				1: Unknown
				2: No Init
				3: Quick Init
				4: Full Init"
			::= { logicalDriveDescriptionEntry 21 }	
			
		logicalDriveBGIEnable OBJECT-TYPE
			SYNTAX INTEGER
			{
				unknown(1),			
				disabled(2),
				enabled(3)
			}			
			MAX-ACCESS read-write
			STATUS current
			DESCRIPTION
				"Information about logical drive BGI state.
				1: Unknown (read only)
				2: Disabled
				3: Enabled
				
				Note: Set action is not available when logical drive is used for secondary cache(logicalDriveIsSSCD = Yes)."
			::= { logicalDriveDescriptionEntry 22 }	

		logicalDriveIsSSCD OBJECT-TYPE
			SYNTAX INTEGER
			{
				unknown(1),			
				no(2),
				yes(3)
			}			
			MAX-ACCESS read-only
			STATUS current
			DESCRIPTION
				"Information about logical drive if it is used for secondary cache.
				1: Unknown
				2: No
				3: Yes"
			::= { logicalDriveDescriptionEntry 23 }	
			
		logicalDriveSSCDCachingEnable OBJECT-TYPE
			SYNTAX INTEGER
			{
				unknown(1),			
				disabled(2),
				enabled(3)
			}			
			MAX-ACCESS read-write
			STATUS current
			DESCRIPTION
				"Information about logical drive SSCD caching state if it is not used for secondary cache and 
				it's participated physical drives are not SSD.
				1: Unknown (read only)
				2: Disabled
				3: Enabled"
			::= { logicalDriveDescriptionEntry 24 }	
			
		logicalDriveAssociatedLDs OBJECT-TYPE
			SYNTAX DisplayString			
			MAX-ACCESS read-only
			STATUS current
			DESCRIPTION
				"Information about logical drive associated logical drives IDs seperated by commas if it is used for secondary cache."
			::= { logicalDriveDescriptionEntry 25 }	
							
		logicalDriveDedicatedSparePD OBJECT-TYPE
			SYNTAX DisplayString			
			MAX-ACCESS read-only
			STATUS current
			DESCRIPTION
				"Information about logical drive dedicated hot spare physical drives IDs seperated by commas."
			::= { logicalDriveDescriptionEntry 26 }	
							
		logicalDriveDelete OBJECT-TYPE
			SYNTAX INTEGER			
			MAX-ACCESS read-write
			STATUS current
			DESCRIPTION
				"Delete logical drive (write only). The argument is :
				1: delete
				others: invalid"
			::= { logicalDriveDescriptionEntry 27 }	
		
		logicalDriveOSLetter OBJECT-TYPE
			SYNTAX DisplayString			
			MAX-ACCESS read-only
			STATUS current
			DESCRIPTION
				"Information about logical drive OS letter."
			::= { logicalDriveDescriptionEntry 28 }	
				
--  ****************** Disk Array information **********************

		diskArrayProperty OBJECT IDENTIFIER ::= { hwiBMC 39 } 

		diskArrayDescriptionTable OBJECT-TYPE
			SYNTAX SEQUENCE OF DiskArrayDescriptionEntry 
			MAX-ACCESS not-accessible
			STATUS current
			DESCRIPTION
				"A table containing the disk array managed by RAID controller."
			::= { diskArrayProperty 50 }
        
                diskArrayDescriptionEntry OBJECT-TYPE
			SYNTAX DiskArrayDescriptionEntry 
			MAX-ACCESS not-accessible
			STATUS current
			DESCRIPTION
				"Information about logical drive."
			INDEX { diskArrayRAIDControllerIndex, diskArrayIndex }
			::= { diskArrayDescriptionTable 1 }
		
		DiskArrayDescriptionEntry ::=
			SEQUENCE {
				diskArrayRAIDControllerIndex
					INTEGER,
				diskArrayIndex
					INTEGER,					
				diskArrayUsedSpaceInMB
					INTEGER,
				diskArrayFreeSpaceInMB
					INTEGER,
				diskArrayLDCount
					INTEGER, 
				diskArrayLDId
					DisplayString,
				diskArrayPDCount
					INTEGER,
				diskArrayPDId
					DisplayString
				}	

		diskArrayRAIDControllerIndex OBJECT-TYPE
			SYNTAX INTEGER
			MAX-ACCESS not-accessible
			STATUS current
			DESCRIPTION
				"Information about RAID controller index to which this disk array belongs."
			::= { diskArrayDescriptionEntry 1 }			

		diskArrayIndex OBJECT-TYPE
			SYNTAX INTEGER
			MAX-ACCESS not-accessible
			STATUS current
			DESCRIPTION
				"Information about disk array index in current RAID controller."
			::= { diskArrayDescriptionEntry 2 }			
			
		diskArrayUsedSpaceInMB OBJECT-TYPE
			SYNTAX INTEGER
			{
				unknown(4294967295)
			}
			MAX-ACCESS read-only
			STATUS current
			DESCRIPTION
				"Information about the used space in MB of disk array."
			::= { diskArrayDescriptionEntry 3 }				
											   											   
		diskArrayFreeSpaceInMB OBJECT-TYPE
			SYNTAX INTEGER
			{
				unknown(4294967295)
			}
			MAX-ACCESS read-only
			STATUS current
			DESCRIPTION
				"Information about the free space in MB of disk array."
			::= { diskArrayDescriptionEntry 4 }

		diskArrayLDCount OBJECT-TYPE
			SYNTAX INTEGER
			{
				unknown(255)
			}
			MAX-ACCESS read-only
			STATUS current
			DESCRIPTION
				"Information about logical drive count in the disk array."
			::= { diskArrayDescriptionEntry 5 }
				
		diskArrayLDId OBJECT-TYPE
			SYNTAX DisplayString
			MAX-ACCESS read-only
			STATUS current
			DESCRIPTION
				"Information about logical drive IDs in the disk array, seperated by commas."
			::= { diskArrayDescriptionEntry 6 }

		diskArrayPDCount OBJECT-TYPE
			SYNTAX INTEGER
			{
				unknown(255)
			}			
			MAX-ACCESS read-only
			STATUS current
			DESCRIPTION
				"Information about physical drive count in the disk array."
			::= { diskArrayDescriptionEntry 7 }
				
		diskArrayPDId OBJECT-TYPE
			SYNTAX DisplayString
			MAX-ACCESS read-only
			STATUS current
			DESCRIPTION
				"Information about physical drive IDs in the disk array, seperated by commas."
			::= { diskArrayDescriptionEntry 8 }		

--    ****** remoteControl Information *******************************

		remoteControl OBJECT IDENTIFIER ::= { hwiBMC 40 }

		localKVMState OBJECT-TYPE
			SYNTAX INTEGER
			{
				disable(1),
				enable(2)
			}
			MAX-ACCESS read-write
			STATUS current
			DESCRIPTION
				"Local KVM display state. disable 1, enable 2.
				Default value is enable(2)."
			::= { remoteControl 1 }

--    ****** two-factor authentication Location *******************************

		twoFactorAuthentication  OBJECT IDENTIFIER ::= { hwiBMC 41 }

  		twoFactorAuthenticationEnable OBJECT-TYPE
			SYNTAX INTEGER
					{
					disable (1),
					enable (2)
					}
			MAX-ACCESS read-write
			STATUS current
			DESCRIPTION
				"The enable state of two-factor authentication.
				disable 1, enable 2.
				Default value is disable(1)."
			::= { twoFactorAuthentication 1 }

		twoFactorAuthenticationRevocationCheck OBJECT-TYPE
			SYNTAX INTEGER
			{
			disable (1),
			enable (2)
			}

			MAX-ACCESS read-write
			STATUS current
			DESCRIPTION
				"The enable state of certificate revocation check.
				disable 1, enable 2.
				Default value is disable(1)."
			::= { twoFactorAuthentication 2 }

		--root certificate
		rootCertificateDescriptionTable OBJECT-TYPE
			SYNTAX SEQUENCE OF RootCertificateDescriptionEntry
			MAX-ACCESS not-accessible
			STATUS current
			DESCRIPTION
				"A table containing the list of root certificate information."
			::= { twoFactorAuthentication 50 }

		rootCertificateDescriptionEntry OBJECT-TYPE
			SYNTAX RootCertificateDescriptionEntry
			MAX-ACCESS not-accessible
			STATUS current
			DESCRIPTION
				"Information about root certificate."
			INDEX { rootCertificateIndex }
			::= { rootCertificateDescriptionTable 1 }

		RootCertificateDescriptionEntry ::=
			SEQUENCE {
				rootCertificateIndex
					INTEGER,
				rootCertificateIssuedTo
					DisplayString,
				rootCertificateIssuedBy
					DisplayString,
				rootCertificateValidFrom
					DisplayString,
				rootCertificateValidTo
					DisplayString,
				rootCertificateSerialNumber
					DisplayString,
				rootCertificateImport
					DisplayString,
				rootCertificateDelete
					INTEGER
				}

		rootCertificateIndex OBJECT-TYPE
			SYNTAX INTEGER
			MAX-ACCESS not-accessible
			STATUS current
			DESCRIPTION
				""
			::= { rootCertificateDescriptionEntry 1 }

		rootCertificateIssuedTo OBJECT-TYPE
			SYNTAX DisplayString
			MAX-ACCESS read-only
			STATUS current
			DESCRIPTION
				"root certificate subject."
			::= { rootCertificateDescriptionEntry 2 }

		rootCertificateIssuedBy OBJECT-TYPE
			SYNTAX DisplayString
			MAX-ACCESS read-only
			STATUS current
			DESCRIPTION
				"root certificate issuer."
			::= { rootCertificateDescriptionEntry 3 }

		rootCertificateValidFrom OBJECT-TYPE
			SYNTAX DisplayString
			MAX-ACCESS read-only
			STATUS current
			DESCRIPTION
				"root certificate valid start data."
			::= { rootCertificateDescriptionEntry 4 }

		rootCertificateValidTo OBJECT-TYPE
			SYNTAX DisplayString
			MAX-ACCESS read-only
			STATUS current
			DESCRIPTION
				"root certificate valid end date."
			::= { rootCertificateDescriptionEntry 5 }

		rootCertificateSerialNumber OBJECT-TYPE
			SYNTAX DisplayString
			MAX-ACCESS read-only
			STATUS current
			DESCRIPTION
				"root certificate serial number."
			::= { rootCertificateDescriptionEntry 6 }

		rootCertificateImport OBJECT-TYPE
			SYNTAX DisplayString
			MAX-ACCESS read-write
			STATUS current
			DESCRIPTION
				"Import root certificate,write only. eg:/tmp/cacert.pem"
			::= { rootCertificateDescriptionEntry 7 }

		rootCertificateDelete OBJECT-TYPE
			SYNTAX INTEGER
			MAX-ACCESS read-write
			STATUS current
			DESCRIPTION
				"Information about delete root certificate.
				This vaule will be one of the following:
				(delete(1))."
			::= { rootCertificateDescriptionEntry 8 }

		--client certificate
		clientCertificateDescriptionTable OBJECT-TYPE
			SYNTAX SEQUENCE OF ClientCertificateDescriptionEntry
			MAX-ACCESS not-accessible
			STATUS current
			DESCRIPTION
				"A table containing the list of client certificate information."
			::= { twoFactorAuthentication 51 }

		clientCertificateDescriptionEntry OBJECT-TYPE
			SYNTAX ClientCertificateDescriptionEntry
			MAX-ACCESS not-accessible
			STATUS current
			DESCRIPTION
				"Information about client certificate."
			INDEX { clientCertificateIndex }
			::= { clientCertificateDescriptionTable 1 }

		ClientCertificateDescriptionEntry ::=
			SEQUENCE {
				clientCertificateIndex
					INTEGER,
				clientCertificateFingerPrint
					DisplayString,
				clientCertificateImport
					DisplayString,
				clientCertificateDelete
					INTEGER
				}

		clientCertificateIndex OBJECT-TYPE
			SYNTAX INTEGER
			MAX-ACCESS not-accessible
			STATUS current
			DESCRIPTION
				""
			::= { clientCertificateDescriptionEntry 1 }

		clientCertificateFingerPrint OBJECT-TYPE
			SYNTAX DisplayString
			MAX-ACCESS read-only
			STATUS current
			DESCRIPTION
				"The client certificate finger print."
			::= { clientCertificateDescriptionEntry 2 }

		clientCertificateImport OBJECT-TYPE
			SYNTAX DisplayString
			MAX-ACCESS read-write
			STATUS current
			DESCRIPTION
				"Import client certificate,write only. eg:/tmp/clientcert.pem"
			::= { clientCertificateDescriptionEntry 3 }

		clientCertificateDelete OBJECT-TYPE
			SYNTAX INTEGER
			MAX-ACCESS read-write
			STATUS current
			DESCRIPTION
				"Information about delete client certificate.
				This vaule will be one of the following:
				(delete(1))."
			::= { clientCertificateDescriptionEntry 4 }
			
--    ****** configuration Information *******************************
		configuration OBJECT IDENTIFIER ::= { hwiBMC 42 }
		
		exportconfig OBJECT-TYPE
				SYNTAX DisplayString
				MAX-ACCESS read-write
				STATUS current
				DESCRIPTION
					"Starting to export all configuration of BMC , BIOS and RAID Controller.
					 The exported RAID Controller configurations are valid only if they are exported after the POST is complete.
					 The input parameter is file path or URL of configuration file.
					 Filepath  e.g.: /tmp/config.xml
					 File URL      : protocol://username:password@IP:[port]/directory/filename
						 The parameters in the URL are described as follows:
						 The protocol must be https,sftp,cifs,scp or nfs.
						 The username and password are those of the destination server.
						 The directory and filename are those on the destination server."
				::= { configuration 1 }

		importconfig OBJECT-TYPE
				SYNTAX DisplayString
				MAX-ACCESS read-write
				STATUS current
				DESCRIPTION
					"Starting to import all configuration of BMC , BIOS and RAID Controller.
					 The input parameter is file path or URL of configuration file.
					 Filepath  e.g.: /tmp/config.xml
					 File URL      : protocol://username:password@IP:[port]/directory/filename
						 The parameters in the URL are described as follows:
						 The protocol must be https,sftp,cifs,scp or nfs.
						 The username and password are those of the destination server.
						 The directory and filename are those on the destination server."
				::= { configuration 2 }
		
		configprogress OBJECT-TYPE
				SYNTAX DisplayString
				MAX-ACCESS read-only
				STATUS current
				DESCRIPTION
					"Query the progress of exporting/importing all configuration of BMC , BIOS and RAID Controller.
					 Query the progress of uploading configuration file to remote host or download configuration file from remote host.
					 The positive value means percentage of exporting/importing or uploading/downloading.
					 The negative value(-1) means error."
				::= { configuration 3 }
		
		configerrorinfo OBJECT-TYPE
				SYNTAX DisplayString
				MAX-ACCESS read-only
				STATUS current
				DESCRIPTION
					"Query the error information of exporting/importing all configuration of BMC , BIOS and RAID Controller.
					 Query the error information of uploading configuration file to remote host or download configuration file from remote host.
					 If error happened, configerrorinfo value shows the error information.
					 If error don't happened, configerrorinfo value is null."
				::= { configuration 4 }
			
		businessPortProperty OBJECT IDENTIFIER ::= { hwiBMC 43 }    

		businessPortDescriptionTable OBJECT-TYPE
			SYNTAX SEQUENCE OF BusinessPortDescriptionEntry 
			MAX-ACCESS not-accessible
			STATUS current
			DESCRIPTION
				"A table containing the net card business port information."
			::= { businessPortProperty 50 }

		businessPortDescriptionEntry  OBJECT-TYPE
			SYNTAX BusinessPortDescriptionEntry 
			MAX-ACCESS not-accessible
			STATUS current
			DESCRIPTION
				"Information about net card business port."
			INDEX { businessPortIndex }
			::= { businessPortDescriptionTable 1 }
		
		BusinessPortDescriptionEntry  ::=
			SEQUENCE {
				businessPortIndex
					INTEGER,
				businessPortSilkNum
					INTEGER,
				businessPortLocation
					DisplayString,
				businessPortLinkStatus 
					DisplayString,
				businessPortMacAddr
					DisplayString,
				businessPortBDF
					DisplayString
				}
				 
		
		businessPortIndex OBJECT-TYPE	
			SYNTAX INTEGER
			MAX-ACCESS not-accessible
			STATUS current
			DESCRIPTION
				" Information about business port logical resource index within all net card."
			::= { businessPortDescriptionEntry 1 } 

		
		businessPortSilkNum OBJECT-TYPE	
			SYNTAX INTEGER
			MAX-ACCESS read-only
			STATUS current
			DESCRIPTION
				" Information about business port silk number within a net card."
			::= { businessPortDescriptionEntry 2 } 
			
		
		businessPortLocation OBJECT-TYPE
			SYNTAX DisplayString
			MAX-ACCESS read-only
			STATUS current
			DESCRIPTION
				" Information about businessport belongs to which net card."
			::= { businessPortDescriptionEntry 3 }

		
		businessPortLinkStatus OBJECT-TYPE
			SYNTAX DisplayString
			MAX-ACCESS read-only
			STATUS current
			DESCRIPTION
				" Business port link status."
			::= { businessPortDescriptionEntry 4 }  
 
		
		businessPortMacAddr OBJECT-TYPE
			SYNTAX DisplayString
			MAX-ACCESS read-only
			STATUS current
			DESCRIPTION
				" Business port MAC address."
			::= { businessPortDescriptionEntry 5 }
			
		businessPortBDF OBJECT-TYPE
			SYNTAX DisplayString
			MAX-ACCESS read-only
			STATUS current
			DESCRIPTION
				" Business port BDF."
			::= { businessPortDescriptionEntry 6 }


END
